FME workspace TPWD Data to AGO.fmw

Creator
    GEOMTYPE = Geometry Object
    NUM = 1
    CREATED -> FeatureReader_2 [INITIATOR]
    CREATED -> HTTPCaller_2
    CREATED -> FeatureReader_4 [INITIATOR]
Note: TPWD AGO
FeatureReader_4
    ARCGISFEATURES_ALIAS_MODE = NONE
    ARCGISFEATURES_AUTH_TYPE = None
    ARCGISFEATURES_CREATE_FEATURE_TABLES_FROM_DATA = Yes
    ARCGISFEATURES_FEATURES_PER_REQUEST = 1000
    ARCGISFEATURES_FORMAT_GUID = YES
    ARCGISFEATURES_QUERY_FEATURE_TYPES_FOR_MERGE_FILTERS = Yes
    ARCGISFEATURES_RESOLVE_DOMAINS = Yes
    ARCGISFEATURES_USE_SEARCH_ENVELOPE = NO
    ARCGISFEATURES_VERIFY_HTTPS = Yes
    ATTRIBUTES = "Bridge Points","OBJECTID,LoCode,LoCode_resolved,ParkName,ParkName_resolved,Category,Category_resolved,Name1,Type,Type_resolved,LowWater,LowWater_resolved,Material,Material_resolved,WidthFT,LengthFT,AreaSQFT,ADA,ADA_resolved,RTname,Traverses,LoadLimits,Historic,Historic_resolved,PropNo,AssetID,UTMZone,UTMZone_resolved,UTMX,UTMY,DMSX,DMSY,DDX,DDY,DDMX,DDMY,SrcType,SrcName,SrcOrigin,SrcScale,SrcDate,DataOrigin,DataDate,EditDate,Editor,GlobalID,Creator,CreatedDate,LastEditor,LastEditDate","Buildings and Structures","OBJECTID,LoCode,LoCode_resolved,ParkName,ParkName_resolved,Category,BldgStruc,BldgStruc_resolved,PropNo,Descriptor,Descriptor_resolved,NameProper,NameFunction,Lineage,ConstType,ConstType_resolved,ConstDate,CalcSF,InteriorSF,BldgDIM,BldgADA,BldgADA_resolved,Location,SiteNumber,NatlRegiser,NatlRegiser_resolved,Historic,Historic_resolved,Comments,UTMZone,UTMZone_resolved,SrcType,SrcName,SrcOrigin,SrcScale,SrcDate,DataOrigin,DataDate,EditDate,Editor,GlobalID,Creator,CreatedDate,LastEditor,LastEditDate",Campgrounds,"OBJECTID,LoCode,LoCode_resolved,ParkName,ParkName_resolved,Campground,SiteNumber,SiteClass,SiteClass_resolved,SiteAccess,SiteAccess_resolved,Historic,Historic_resolved,PropNo,Comments,UTMZone,UTMZone_resolved,UTMX,UTMY,DMSX,DMSY,DDX,DDY,DDMX,DDMY,SrcType,SrcName,SrcOrigin,SrcScale,SrcDate,DataOrigin,DataDate,EditDate,Editor,GlobalID,Creator,CreatedDate,LastEditor,LastEditDate","Day Use","OBJECTID,LoCode,LoCode_resolved,ParkName,ParkName_resolved,SiteName,AcresCalc,Comments,UTMZone,UTMZone_resolved,UTMX,UTMY,DMSX,DMSY,DDX,DDY,DDMX,DDMY,SrcType,SrcName,SrcOrigin,SrcScale,SrcDate,DataOrigin,DataDate,EditDate,Editor,GlobalID,Creator,CreatedDate,LastEditor,LastEditDate","Gate Points","OBJECTID,LoCode,LoCode_resolved,ParkName,ParkName_resolved,EntryType,EntryType_resolved,AccessType,AccessType_resolved,Category,Name,EmergencyUse,EmergencyUse_resolved,Gated,Gated_resolved,Locked,Locked_resolved,Vehicular,Vehicular_resolved,AdjOwner,Historic,Historic_resolved,PropNo,AssetID,Comments,UTMZone,UTMZone_resolved,UTMX,UTMY,DMSX,DMSY,DDX,DDY,DDMX,DDMY,SrcType,SrcName,SrcOrigin,SrcScale,SrcDate,DataOrigin,DataDate,EditDate,Editor,GlobalID,Creator,CreatedDate,LastEditor,LastEditDate","Park HQ Points","OBJECTID,LoCode,LoCode_resolved,ParkName,ParkName_resolved,Type,County,Phone,Street,City,Zip,Comments,URL,Directions,Availability,UseType,UTMZone,UTMX,UTMY,DMSX,DMSY,DDX,DDY,WebMerc84X,WebMerc84Y,SrcType,SrcName,SrcOrigin,SrcScale,SrcDate,DataOrigin,DataDate,EditDate,Editor,GlobalID,Status,Creator,CreatedDate,LastEditor,LastEditDate","Park Regions","OBJECTID,Region,Comments,SrcType,SrcName,SrcOrigin,SrcScale,SrcDate,DataOrigin,DataDate,EditDate,Editor,GlobalID,Creator,CreatedDate,LastEditor,LastEditDate,Shape_Length,Shape_Area","Road Lines","OBJECTID,LoCode,LoCode_resolved,ParkName,ParkName_resolved,Desgntn,Desgntn_resolved,Name1,Name2,Paved,Paved_resolved,Material,Material_resolved,Access,Access_resolved,TPWDclass,TPWDclass_resolved,CertMile,CertDate,WidthFT,Miles,Historic,Historic_resolved,PropNo,AssetID,Comments,UTMZone,UTMZone_resolved,SrcType,SrcName,SrcOrigin,SrcScale,SrcDate,DataOrigin,DataDate,EditDate,Editor,GlobalID,Creator,CreatedDate,LastEditor,LastEditDate,Shape_Length","TPWD Properties","OBJECTID,LoCode,LoCode_resolved,LoName,LoName_resolved,BndryType,BndryType_resolved,TPWDivision,TPWDivision_resolved,County1,County1_resolved,County2,County2_resolved,County3,County3_resolved,County4,County4_resolved,CalcAcres,DeedAcres,Comments,UTMZone,SrcType,SrcName,SrcOrigin,SrcScale,SrcDate,DataOrigin,DataDate,EditDate,Editor,Creator,CreatedDate,LastEditor,LastEditDate,GlobalID_1,OrgCode,OrgCode_resolved,Shape_Length,Shape_Area","Trail Lines","OBJECTID,LoCode,LoCode_resolved,ParkName,ParkName_resolved,SegNum,Official,Official_resolved,Name1,Name2,Name3,Name4,Name5,Name6,PublicTrail,ADA,TrailRating,TrailClosure,TrailSurface,TrailSurface_resolved,Tracktype,Tracktype_resolved,TrailUse,TrailUse_resolved,LengthFT,LengthMI,TotalRiseFT,PctGrade,Historic,Historic_resolved,AssetID,Comments,UTMZone,UTMZone_resolved,SrcType,SrcName,SrcOrigin,SrcScale,SrcDate,DataOrigin,DataDate,EditDate,Editor,GlobalID,Creator,CreatedDate,LastEditor,LastEditDate,Shape_Length","Utility Lines","OBJECTID,UtiltiyLnID,LoCode,LoCode_resolved,ParkName,ParkName_resolved,Service,Descriptor,Descriptor_resolved,Type,Type_resolved,Placement,Placement_resolved,Historic,Historic_resolved,FireHazard,FireHazard_resolved,Comments,UTMZone,UTMZone_resolved,SrcType,SrcName,SrcOrigin,SrcScale,SrcDate,DataOrigin,DataDate,EditDate,Editor,GlobalID,Creator,CreatedDate,LastEditor,LastEditDate,Shape_Length","Utility Points","OBJECTID,UtiltiyPtID,LoCode,LoCode_resolved,ParkName,ParkName_resolved,Service,Descriptor,Descriptor_resolved,Placement,Placement_resolved,Historic,Historic_resolved,FireHazard,FireHazard_resolved,Comments,UTMZone,UTMZone_resolved,UTMX,UTMY,DMSX,DMSY,DDX,DDY,DDMX,DDMY,SrcType,SrcName,SrcOrigin,SrcScale,SrcDate,DataOrigin,DataDate,EditDate,Editor,GlobalID,EffectUsge,Key_EU,Creator,CreatedDate,LastEditor,LastEditDate","Water Flow Lines","OBJECTID,LoCode,LoCode_resolved,ParkName,ParkName_resolved,FID_NHDFlowlines24k,COMID,FDATE,RESOLUTION,GNIS_ID,GNIS_NAME,LENGTHKM,REACHCODE,FLOWDIR,WBAREACOMID,FTYPE,FCODE,Comments,UTMZone,UTMZone_resolved,SrcType,SrcName,SrcOrigin,SrcScale,SrcDate,DataOrigin,DataDate,EditDate,Editor,GlobalID,Creator,CreatedDate,LastEditor,LastEditDate,Shape_Length"
    ATTR_ACCUM_MODE = Only Use Result
    COMBINE_GEOM = Use Result
    DATASET = https://tpwd.texas.gov/server/rest/services/Cultural/NRV_DEV_for_CRViewer_on_PRO/MapServer
    FEATURETYPES = Buildings and Structures Campgrounds Day Use Road Lines TPWD Properties Trail Lines Utility Points
    FORMAT = ARCGISFEATURES
    GEOMETRY_TYPES = "Bridge Points",""",fme_point""","Buildings and Structures",""",fme_point""",Campgrounds,""",fme_point""","Day Use",""",fme_point""","Gate Points",""",fme_point""","Park HQ Points",""",fme_point""","Park Regions",""",fme_area""","Road Lines",""",fme_line""","TPWD Properties",""",fme_area""","Trail Lines",""",fme_line""","Utility Lines",""",fme_line""","Utility Points",""",fme_point""","Water Flow Lines",""",fme_line"""
    INTERACT = NONE
    ORDER_RESULTS = No
    OUTPUT_ADD_SCHEMA_ATTRIBUTES = NO
    OUTPUT_FEATURES_DISPLAY = Schema and Data Features
    Buildings and Structures -> AttributeManager_7
    Buildings and Structures -> NullAttributeCounter
    Campgrounds -> AttributeManager
    Day Use -> AttributeManager_5
    Road Lines -> AttributeManager_8
    TPWD Properties -> AttributeManager_4
    Trail Lines -> AttributeManager_6
    Utility Points -> AttributeManager_9
FeatureWriter_2
    ARCGISONLINEFEATURES_ASYNC_WRITE = NO
    ARCGISONLINEFEATURES_DESTINATION_DATASETTYPE_VALIDATION = Yes
    ARCGISONLINEFEATURES_EXISTING_FEATURE_SERVICE_HANDLING = USE_EXISTING
    ARCGISONLINEFEATURES_FEATURESERVICE_NAME = Campgrounds
    ARCGISONLINEFEATURES_FEATURES_PER_REQUEST = 1000
    ARCGISONLINEFEATURES_FEATURE_SERVICE_CREATE_FILEGDB = NO
    ARCGISONLINEFEATURES_FEATURE_SERVICE_HANDLING = CREATE_IF_MISSING
    ARCGISONLINEFEATURES_FEATURE_SERVICE_SELECTION_SOURCE = User
    ARCGISONLINEFEATURES_FOLDER_NAME = Camping
    ARCGISONLINEFEATURES_NC = Spatialty AGO
    ARCGISONLINEFEATURES_TARGET_WKID = 102100
    ARCGISONLINEFEATURES_USE_GLOBAL_ID = No
    DATASET_ATTR = _dataset
    FEATURE_TYPE_LIST_ATTR = _feature_types
    FORMAT = ARCGISONLINEFEATURES
    TOTAL_FEATURES_WRITTEN_ATTR = _total_features_written
Note: Write to AGO
FeatureWriter [off]
    ARCGISONLINEFEATURES_DESTINATION_DATASETTYPE_VALIDATION = Yes
    ARCGISONLINEFEATURES_FEATURESERVICE = camping
    ARCGISONLINEFEATURES_FEATURES_PER_REQUEST = 1000
    ARCGISONLINEFEATURES_NC = Mike Does GIS
    ARCGISONLINEFEATURES_TARGET_WKID = 102100
    ARCGISONLINEFEATURES_USE_GLOBAL_ID = No
    DATASET_ATTR = _dataset
    FEATURE_TYPE_LIST_ATTR = _feature_type
    FORMAT = ARCGISONLINEFEATURES
    TOTAL_FEATURES_WRITTEN_ATTR = _total_features_written

Bookmark: Utils
NullAttributeCounter
Esri_AttributeFieldChecker

Bookmark: Rename and Clean Attributes and Records
AttributeManager_7
    ATTR_TABLE:
      REMOVE OBJECTID (int32)
      REMOVE LoCode (varchar(5))
      RENAME_SET_VALUE LoCode_resolved > LoCode (buffer)
      REMOVE ParkName (varchar(50))
      RENAME_SET_VALUE ParkName_resolved > ParkName (buffer)
      REMOVE PropNo (varchar(50))
      REMOVE ConstType (varchar(150))
      REMOVE ConstDate (varchar(8))
      REMOVE CalcSF (real64)
      REMOVE InteriorSF (real64)
      REMOVE BldgDIM (varchar(50))
      REMOVE BldgStruc_resolved (buffer)
      REMOVE BldgADA (varchar(3))
      REMOVE SiteNumber (varchar(8))
      REMOVE NatlRegiser (varchar(3))
      REMOVE Historic (varchar(50))
      REMOVE UTMZone (int16)
      REMOVE SrcType (varchar(50))
      REMOVE SrcName (varchar(50))
      REMOVE SrcOrigin (varchar(50))
      REMOVE SrcScale (varchar(10))
      REMOVE SrcDate (varchar(8))
      REMOVE DataOrigin (varchar(16))
      REMOVE DataDate (varchar(8))
      REMOVE EditDate (varchar(8))
      REMOVE Editor (varchar(16))
      REMOVE GlobalID (varchar(38))
      REMOVE Creator (varchar(255))
      REMOVE CreatedDate (datetime)
      REMOVE LastEditor (varchar(255))
      REMOVE LastEditDate (datetime)
      REMOVE Descriptor_resolved (buffer)
      REMOVE ConstType_resolved (buffer)
      REMOVE BldgADA_resolved (buffer)
      REMOVE NatlRegiser_resolved (buffer)
      REMOVE Historic_resolved (buffer)
      REMOVE UTMZone_resolved (buffer)
    -> NullAttributeMapper_3
NullAttributeMapper_3
    ATTRCHOICE_ACTION = SELECTED
    ATTRLIST = Comments BldgStruc Category Descriptor Lineage Location LoCode NameFunction NameProper ParkName
    NULL_TREATMENT_LU = SETNULL
    OTHER_VALUE = " "
    SOURCE_ATTR_VAL_LU = EMPTY MISSINGATTR
    ATTRCHOICE = Selected Attributes
    NULL_TREATMENT = Null
    SOURCE_ATTR_VAL = Empty "Missing (Selected Attributes Only)"
    -> AttributeValueMapper
AttributeValueMapper
    LUT = 0,Administrative Operations,1,Restrooms,2,Visitor,3,Water Structures
    MAPPING_DIRECTION = FORWARD
    SRC = Category
    VAL_ATTR = Category
    -> FeatureWriter_2 [Output00]
AttributeManager
    ATTR_TABLE:
      REMOVE OBJECTID (int32)
      REMOVE LoCode (varchar(5))
      RENAME_SET_VALUE LoCode_resolved > LoCode (buffer)
      REMOVE ParkName (varchar(50))
      RENAME_SET_VALUE ParkName_resolved > ParkName (buffer)
      REMOVE SiteClass (varchar(25))
      RENAME_SET_VALUE SiteClass_resolved > SiteClass (buffer)
      REMOVE SiteAccess (varchar(15))
      RENAME_SET_VALUE SiteAccess_resolved > SiteAccess (buffer)
      REMOVE Historic (varchar(50))
      REMOVE UTMZone (int16)
      REMOVE UTMX (real64)
      REMOVE UTMY (real64)
      REMOVE DMSX (varchar(20))
      REMOVE DMSY (varchar(20))
      REMOVE DDX (real64)
      REMOVE DDY (real64)
      REMOVE DDMX (varchar(15))
      REMOVE DDMY (varchar(15))
      REMOVE SrcType (varchar(50))
      REMOVE SrcName (varchar(50))
      REMOVE SrcOrigin (varchar(50))
      REMOVE SrcScale (varchar(10))
      REMOVE SrcDate (varchar(8))
      REMOVE DataOrigin (varchar(16))
      REMOVE DataDate (varchar(8))
      REMOVE EditDate (varchar(8))
      REMOVE Editor (varchar(16))
      REMOVE GlobalID (varchar(38))
      REMOVE Creator (varchar(255))
      REMOVE CreatedDate (datetime)
      REMOVE LastEditor (varchar(255))
      REMOVE LastEditDate (datetime)
      REMOVE Historic_resolved (buffer)
      REMOVE UTMZone_resolved (buffer)
    -> NullAttributeMapper_2
NullAttributeMapper_2
    ATTRCHOICE_ACTION = SELECTED
    ATTRLIST = Comments Campground LoCode ParkName PropNo SiteAccess SiteClass SiteNumber
    NULL_TREATMENT_LU = SETNULL
    OTHER_VALUE = " "
    SOURCE_ATTR_VAL_LU = EMPTY MISSINGATTR
    ATTRCHOICE = Selected Attributes
    NULL_TREATMENT = Null
    SOURCE_ATTR_VAL = Empty "Missing (Selected Attributes Only)"
    -> FeatureWriter_2 [Output]
AttributeManager_5
    ATTR_TABLE:
      REMOVE OBJECTID (int32)
      REMOVE LoCode (varchar(5))
      RENAME_SET_VALUE LoCode_resolved > LoCode (buffer)
      REMOVE ParkName (varchar(50))
      RENAME_SET_VALUE ParkName_resolved > ParkName (buffer)
      REMOVE AcresCalc (real64)
      REMOVE UTMZone (int16)
      REMOVE UTMZone_resolved (buffer)
      REMOVE UTMX (real64)
      REMOVE UTMY (real64)
      REMOVE DMSX (varchar(20))
      REMOVE DMSY (varchar(20))
      REMOVE DDMX (varchar(15))
      REMOVE DDMY (varchar(15))
      REMOVE SrcType (varchar(50))
      REMOVE SrcName (varchar(50))
      REMOVE SrcOrigin (varchar(50))
      REMOVE SrcScale (varchar(10))
      REMOVE SrcDate (varchar(8))
      REMOVE DataOrigin (varchar(16))
      REMOVE DataDate (varchar(8))
      REMOVE EditDate (varchar(8))
      REMOVE Editor (varchar(16))
      REMOVE GlobalID (varchar(38))
      REMOVE Creator (varchar(255))
      REMOVE CreatedDate (datetime)
      REMOVE LastEditor (varchar(255))
      REMOVE LastEditDate (datetime)
    -> NullAttributeMapper_4
NullAttributeMapper_4
    ATTRCHOICE_ACTION = SELECTED
    ATTRLIST = Comments DDX DDY LoCode ParkName SiteName
    NULL_TREATMENT_LU = SETNULL
    OTHER_VALUE = " "
    SOURCE_ATTR_VAL_LU = EMPTY MISSINGATTR
    ATTRCHOICE = Selected Attributes
    NULL_TREATMENT = Null
    SOURCE_ATTR_VAL = Empty "Missing (Selected Attributes Only)"
    -> FeatureWriter_2 [Output01]
AttributeManager_8
    ATTR_TABLE:
      REMOVE OBJECTID (int32)
      REMOVE LoCode (varchar(5))
      RENAME_SET_VALUE LoCode_resolved > LoCode (buffer)
      REMOVE ParkName (varchar(50))
      RENAME_SET_VALUE ParkName_resolved > ParkName (buffer)
      REMOVE Desgntn (varchar(25))
      RENAME_SET_VALUE Desgntn_resolved > Desgntn (buffer)
      REMOVE Paved (varchar(15))
      RENAME_SET_VALUE Paved_resolved > Paved (buffer)
      REMOVE Material (varchar(25))
      REMOVE Material_resolved (buffer)
      REMOVE Access (varchar(15))
      RENAME_SET_VALUE Access_resolved > Access (buffer)
      REMOVE TPWDclass (varchar(12))
      REMOVE TPWDclass_resolved (buffer)
      REMOVE CertMile (real64)
      REMOVE CertDate (real64)
      REMOVE WidthFT (real64)
      REMOVE Miles (real64)
      REMOVE Historic (varchar(10))
      REMOVE Historic_resolved (buffer)
      REMOVE PropNo (varchar(50))
      REMOVE AssetID (int32)
      REMOVE UTMZone (int16)
      REMOVE UTMZone_resolved (buffer)
      REMOVE SrcType (varchar(50))
      REMOVE SrcName (varchar(50))
      REMOVE SrcOrigin (varchar(50))
      REMOVE SrcScale (varchar(10))
      REMOVE SrcDate (varchar(8))
      REMOVE DataOrigin (varchar(16))
      REMOVE DataDate (varchar(8))
      REMOVE EditDate (varchar(8))
      REMOVE Editor (varchar(16))
      REMOVE GlobalID (varchar(38))
      REMOVE Creator (varchar(255))
      REMOVE CreatedDate (datetime)
      REMOVE LastEditor (varchar(255))
      REMOVE LastEditDate (datetime)
      REMOVE Shape_Length (real64)
    -> NullAttributeMapper_5
NullAttributeMapper_5
    ATTRCHOICE_ACTION = SELECTED
    ATTRLIST = Comments Access Desgntn LoCode Name1 Name2 ParkName Paved
    NULL_TREATMENT_LU = SETNULL
    OTHER_VALUE = " "
    SOURCE_ATTR_VAL_LU = EMPTY MISSINGATTR
    ATTRCHOICE = Selected Attributes
    NULL_TREATMENT = Null
    SOURCE_ATTR_VAL = Empty "Missing (Selected Attributes Only)"
    -> FeatureWriter_2 [Output02]
AttributeManager_4
    ATTR_TABLE:
      REMOVE OBJECTID (int32)
      RENAME_SET_VALUE LoCode_resolved > LoCode (buffer)
      REMOVE LoName (varchar(100))
      RENAME_SET_VALUE LoName_resolved > LoName (buffer)
      REMOVE BndryType (varchar(10))
      RENAME_SET_VALUE BndryType_resolved > BndryType (buffer)
      REMOVE TPWDivision (varchar(50))
      RENAME_SET_VALUE TPWDivision_resolved > TPWDivision (buffer)
      REMOVE County1 (varchar(25))
      REMOVE County2 (varchar(25))
      REMOVE County3 (varchar(25))
      REMOVE County4 (varchar(25))
      RENAME_SET_VALUE County1_resolved > County1 (buffer)
      RENAME_SET_VALUE County2_resolved > County2 (buffer)
      RENAME_SET_VALUE County3_resolved > County3 (buffer)
      RENAME_SET_VALUE County4_resolved > County4 (buffer)
      REMOVE DeedAcres (real64)
      SET_TO Comments (varchar(75))
      REMOVE UTMZone (int16)
      REMOVE SrcType (varchar(50))
      REMOVE SrcName (varchar(50))
      REMOVE SrcOrigin (varchar(50))
      REMOVE SrcScale (varchar(10))
      REMOVE SrcDate (varchar(8))
      REMOVE DataOrigin (varchar(16))
      REMOVE DataDate (varchar(8))
      REMOVE EditDate (varchar(8))
      REMOVE Editor (varchar(16))
      REMOVE Creator (varchar(255))
      REMOVE CreatedDate (datetime)
      REMOVE LastEditor (varchar(255))
      REMOVE LastEditDate (datetime)
      REMOVE GlobalID_1 (varchar(38))
      REMOVE OrgCode (varchar(4))
      REMOVE Shape_Length (real64)
      REMOVE Shape_Area (real64)
      REMOVE OrgCode_resolved (buffer)
    -> NullAttributeMapper
NullAttributeMapper
    ATTRCHOICE_ACTION = SELECTED
    ATTRLIST = Comments County1 County2 County3 County4 BndryType CalcAcres LoCode LoName TPWDivision
    NULL_TREATMENT_LU = SETNULL
    OTHER_VALUE = " "
    SOURCE_ATTR_VAL_LU = EMPTY MISSINGATTR
    ATTRCHOICE = Selected Attributes
    NULL_TREATMENT = Null
    SOURCE_ATTR_VAL = Empty "Missing (Selected Attributes Only)"
    -> FeatureWriter_2 [Output03]
AttributeManager_6
    ATTR_TABLE:
      REMOVE OBJECTID (int32)
      REMOVE LoCode (varchar(5))
      RENAME_SET_VALUE LoCode_resolved > LoCode (buffer)
      REMOVE ParkName (varchar(50))
      RENAME_SET_VALUE ParkName_resolved > ParkName (buffer)
      REMOVE Official (varchar(3))
      RENAME_SET_VALUE Official_resolved > Official (buffer)
      REMOVE Name2 (varchar(255))
      REMOVE Name3 (varchar(255))
      REMOVE Name4 (varchar(255))
      REMOVE Name5 (varchar(255))
      REMOVE Name6 (varchar(255))
      REMOVE ADA (varchar(3))
      REMOVE TrailSurface (varchar(30))
      RENAME_SET_VALUE TrailSurface_resolved > TrailSurface (buffer)
      REMOVE Tracktype (varchar(25))
      RENAME_SET_VALUE Tracktype_resolved > Tracktype (buffer)
      REMOVE TrailUse (varchar(30))
      RENAME_SET_VALUE TrailUse_resolved > TrailUse (buffer)
      REMOVE TotalRiseFT (real64)
      REMOVE PctGrade (varchar(50))
      REMOVE Historic (varchar(10))
      REMOVE Historic_resolved (buffer)
      REMOVE AssetID (int32)
      REMOVE UTMZone (int16)
      REMOVE UTMZone_resolved (buffer)
      REMOVE SrcType (varchar(50))
      REMOVE SrcName (varchar(50))
      REMOVE SrcOrigin (varchar(50))
      REMOVE SrcScale (varchar(10))
      REMOVE SrcDate (varchar(8))
      REMOVE DataOrigin (varchar(16))
      REMOVE DataDate (varchar(8))
      REMOVE EditDate (varchar(8))
      REMOVE Editor (varchar(16))
      REMOVE GlobalID (varchar(38))
      REMOVE Creator (varchar(255))
      REMOVE CreatedDate (datetime)
      REMOVE LastEditor (varchar(255))
      REMOVE LastEditDate (datetime)
      REMOVE Shape_Length (real64)
    -> NullAttributeMapper_6
NullAttributeMapper_6
    ATTRCHOICE_ACTION = SELECTED
    ATTRLIST = Comments LengthFT LengthMI LoCode Name1 Official ParkName PublicTrail SegNum TrailClosure TrailRating
    NULL_TREATMENT_LU = SETNULL
    OTHER_VALUE = " "
    SOURCE_ATTR_VAL_LU = EMPTY MISSINGATTR
    ATTRCHOICE = Selected Attributes
    NULL_TREATMENT = Null
    SOURCE_ATTR_VAL = Empty "Missing (Selected Attributes Only)"
    -> FeatureWriter_2 [Output04]
AttributeManager_9
    ATTR_TABLE:
      REMOVE OBJECTID (int32)
      REMOVE UtiltiyPtID (int32)
      REMOVE LoCode (varchar(5))
      RENAME_SET_VALUE LoCode_resolved > LoCode (buffer)
      REMOVE ParkName (varchar(50))
      RENAME_SET_VALUE ParkName_resolved > ParkName (buffer)
      REMOVE Descriptor (varchar(25))
      RENAME_SET_VALUE Descriptor_resolved > Descriptor (buffer)
      REMOVE Placement (varchar(20))
      RENAME_SET_VALUE Placement_resolved > Placement (buffer)
      REMOVE Historic (varchar(50))
      RENAME_SET_VALUE Historic_resolved > Historic (buffer)
      REMOVE FireHazard (varchar(3))
      RENAME_SET_VALUE FireHazard_resolved > FireHazard (buffer)
      REMOVE UTMZone (int16)
      REMOVE UTMZone_resolved (buffer)
      REMOVE UTMX (real64)
      REMOVE UTMY (real64)
      REMOVE DMSX (varchar(20))
      REMOVE DMSY (varchar(20))
      REMOVE DDMX (varchar(15))
      REMOVE DDMY (varchar(15))
      REMOVE SrcType (varchar(50))
      REMOVE SrcName (varchar(50))
      REMOVE SrcOrigin (varchar(50))
      REMOVE SrcScale (varchar(10))
      REMOVE SrcDate (varchar(8))
      REMOVE DataOrigin (varchar(16))
      REMOVE DataDate (varchar(8))
      REMOVE EditDate (varchar(8))
      REMOVE Editor (varchar(16))
      REMOVE GlobalID (varchar(38))
      REMOVE Key_EU (varchar(50))
      REMOVE Creator (varchar(255))
      REMOVE CreatedDate (datetime)
      REMOVE LastEditor (varchar(255))
      REMOVE LastEditDate (datetime)
    -> NullAttributeMapper_7
NullAttributeMapper_7
    ATTRCHOICE_ACTION = SELECTED
    ATTRLIST = Comments DDX DDY Descriptor EffectUsge FireHazard Historic LoCode ParkName Placement Service
    NULL_TREATMENT_LU = SETNULL
    OTHER_VALUE = " "
    SOURCE_ATTR_VAL_LU = EMPTY MISSINGATTR
    ATTRCHOICE = Selected Attributes
    NULL_TREATMENT = Null
    SOURCE_ATTR_VAL = Empty "Missing (Selected Attributes Only)"
    -> AttributeValueMapper_2
    -> Esri_AttributeFieldChecker [Need_to_know_Max_Field_Value_&_Length]
AttributeValueMapper_2
    LUT = 0,Electric,1,Fuel,2,Telecom,3,Water,4,WasteWater,5,Poles or Towers,6,Solid Waste,7,Other
    MAPPING_DIRECTION = FORWARD
    SRC = Service
    VAL_ATTR = Service
    -> FeatureWriter_2 [Output05]

Bookmark: Extract data from map page
HTTPCaller_2 [off]
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = https://tpwd.texas.gov/state-parks/parks-map
    TRANSFER_TIMEOUT_LENGTH = 90
    USE_COOKIES = No
    VERIFY_SSL_CERTIFICATES = Yes
    SAVE_FILE = Attribute
    -> HTMLExtractor [off]
Note: Extract the Javascript / into a list
HTMLExtractor [off]
    HTML_FIELD = @Value(_response_body)
    HTML_SPECIFICATION = Content
    RESULT_TYPE_NAME = LIST_ATTR
    SEARCH_TABLE = jsonResults script Value
    Results -> ListExploder [off]
ListExploder [off]
    ATTR_ACCUM_MODE = Merge List Attributes
    ATTR_CONFLICT_RES_LOOKUP = INCOMING_IF_CONFLICT
    INDEX_ATTR = _element_index
    LIST_ATTR = jsonResults{}
    ATTR_CONFLICT_RES = Use List Attribute Values
    ELEMENTS -> Tester [off]
Tester [off]
    BOOL_OP = OR
    TEST_CLAUSE = CASE_INSENSITIVE_TEST @Value(jsonResults) CONTAINS var jsonResults=
    TEST_MODE = TEST
    PASSED -> StringReplacer_4 [off]
StringReplacer_4 [off]
    CASE = NO
    FIND_TEXT = var jsonResults=
    NO_MATCH = _FME_NO_OP_
    REGEXP = NO
    SRC_ATTRS = jsonResults
    -> JSONFragmenter [off]
JSONFragmenter [off]
    EXPLODE_FORMAT = JSON
    EXTRACT_ATTR = Yes
    JSON_ATTR = jsonResults
    JSON_QUERY = json[*]
    NEW_ATTRIBUTES = name url image idname notices status city longitude latitude address amenities zip
    READ_FROM_FILE = NO
    RECURSIVE_LOOKUP = NO
    REJECT_EMPTY_LISTS = YES
    RECURSIVE = No
    FRAGMENTS -> ListDuplicateRemover [off]
ListDuplicateRemover [off]
    SRC_LIST = location.amenities{}
    -> ListConcatenator [off]
ListConcatenator [off]
    DROP_EMPTY_PARTS = No
    LIST_ATTR = location.amenities{}
    SEP = ", "
    VAL_ATTR = Amenities
    -> ListSorter [off]
ListSorter [off]
    ORDER = Ascending
    SRC_LIST = location.amenities{}
    TYPE = Alphabetic

Bookmark: Mational Park Boundaries
Note: National Parks
FeatureReader_2 [off]
    ARCGISFEATURES_AUTH_TYPE = None
    ARCGISFEATURES_FEATURES_PER_REQUEST = 1000
    ARCGISFEATURES_QUERY_FEATURE_TYPES_FOR_MERGE_FILTERS = Yes
    ARCGISFEATURES_USE_SEARCH_ENVELOPE = NO
    ATTRIBUTES = nps_boundary,"OBJECTID,UNIT_CODE,GIS_Notes,UNIT_NAME,DATE_EDIT,STATE,REGION,GNIS_ID,UNIT_TYPE,CREATED_BY,METADATA,PARKNAME,CreationDate,Creator,EditDate,Editor,Shape__Area,Shape__Length,GlobalID",nps_boundary_centroids,"OBJECTID,UNIT_CODE,UNIT_NAME,DATE_EDIT,STATE,REGION,GNIS_ID,UNIT_TYPE,CREATED_BY,PARKNAME,CreationDate,Creator,EditDate,Editor,GlobalID",nps_tracts,"OBJECTID,TRACT_ID,ALPHA,NPS_DATEU,KEEP,KEY_,ALPHA_TRACT,STATENAME,AREA_TRACT,DEED,ESTATE,STATUS,REGION,ATTRIBUTE,Interest,CreationDate,Creator,EditDate,Editor,Shape__Area,Shape__Length,GlobalID"
    ATTR_ACCUM_MODE = Only Use Result
    COMBINE_GEOM = Use Result
    DATASET = https://services1.arcgis.com/fBc8EJBxQRMcHlei/arcgis/rest/services/NPS_Land_Resources_Division_Boundary_and_Tract_Data_Service/FeatureServer/
    FEATURETYPES = nps_boundary nps_boundary_centroids
    FORMAT = ARCGISFEATURES
    INTERACT = <No Spatial Filter>
    OUTPUT_FEATURES_DISPLAY = Schema and Data Features
    nps_boundary -> AttributeManager_2 [off]
    nps_boundary -> CenterPointReplacer_2 [off]
AttributeManager_2 [off]
    ATTR_TABLE:
      REMOVE OBJECTID
      RENAME_SET_VALUE UNIT_CODE > Park_Home_Page = https://www.nps.gov/@Value(Park_Home_Page)/
      REMOVE GIS_Notes
      REMOVE UNIT_NAME
      REMOVE DATE_EDIT
      REMOVE STATE
      REMOVE REGION
      REMOVE GNIS_ID
      RENAME_SET_VALUE UNIT_TYPE > Type
      REMOVE CREATED_BY
      REMOVE METADATA
      RENAME_SET_VALUE PARKNAME > Name
      REMOVE CreationDate
      REMOVE Creator
      REMOVE EditDate
      REMOVE Editor
      REMOVE Shape__Area
      REMOVE Shape__Length
      REMOVE GlobalID
    -> FeatureWriter [Output] [off]
CenterPointReplacer_2 [off]
    POINTTYPE = CENTER
    POINT -> AttributeManager_3 [off]
AttributeManager_3 [off]
    ATTR_TABLE:
      REMOVE OBJECTID
      REMOVE UNIT_CODE
      REMOVE GIS_Notes
      REMOVE UNIT_NAME
      REMOVE DATE_EDIT
      REMOVE STATE
      REMOVE REGION
      REMOVE GNIS_ID
      REMOVE UNIT_TYPE
      REMOVE CREATED_BY
      REMOVE METADATA
      RENAME_SET_VALUE PARKNAME > Name
      REMOVE CreationDate
      REMOVE Creator
      REMOVE EditDate
      REMOVE Editor
      REMOVE Shape__Area
      REMOVE Shape__Length
      REMOVE GlobalID
    -> FeatureWriter [Point] [off]

FME custom transformer AttributeDataTypeCheck
Used with the Esri_AttributeFieldChecker.fmx

Parameters:
- _ATTR_NAME = @Value(_attr_name)   # Attr Name
- _ATTR_VALUE = @Value(_attr_value)   # Attr Value

DuplicateFilter_6_Input (input)
    -> DuplicateFilter_3
DuplicateFilter_3
    INPUT_ORDERED_CHOICE_LOOKUP = NO
    KEYATTR = _attr_name _attr_value
    PRESERVE_FEATURE_ORDER_LOOKUP = PER_OUTPUT_PORT
    INPUT_ORDERED_CHOICE = No
    UNIQUE -> Junction_18
    UNIQUE -> Junction_2
Junction_18
    -> AttributeValidator_11
    -> AttributeValidator_13
    -> FeatureMerger_Text_Strings_2 [REQUESTOR]
    -> AttributeValidator_15
Junction
    -> Junction_23
Note: AttributeCreator_Numeric : Output
Junction_22
    -> FeatureMerger_Text_Strings_2 [SUPPLIER]
Junction_23
    -> FeatureMerger [SUPPLIER]
Note: FeatureMerger : Requestor
Junction_2
    -> Junction_3
Note: DuplicateFilter_3 : Unique
Junction_3
    -> DuplicateFilter_12
DuplicateFilter_12
    INPUT_ORDERED_CHOICE_LOOKUP = NO
    KEYATTR = _attr_name
    PRESERVE_FEATURE_ORDER_LOOKUP = PER_OUTPUT_PORT
    INPUT_ORDERED_CHOICE = No
    UNIQUE -> FeatureMerger [REQUESTOR]
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(_attr_name) @Value(_attr_name) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> AttributeManager_4
    UNMERGED_REQUESTOR -> AttributeManager_4
AttributeManager_4
    ATTR_TABLE:
      REMOVE _fme_validation_message
      REMOVE Type_Pass_Boolean
      REMOVE _fme_validation_message_list{}
    -> Output:_Attribute_Field_Data_Type_Check (output)
Output:_Attribute_Field_Data_Type_Check (output)

Bookmark: Validate Alphanumeric fields (no special characters)
AttributeValidator_15
    TABLE = _attr_value;TYPE;ALPHANUM
    PASSED -> FeatureMerger_24 [REQUESTOR]
    FAILED -> FeatureMerger_24 [SUPPLIER]
FeatureMerger_24
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(_attr_name) @Value(_attr_name) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    UNMERGED_REQUESTOR -> DuplicateFilter_19
DuplicateFilter_19
    INPUT_ORDERED_CHOICE_LOOKUP = NO
    KEYATTR = _attr_name
    PRESERVE_FEATURE_ORDER_LOOKUP = PER_OUTPUT_PORT
    INPUT_ORDERED_CHOICE = No
    UNIQUE -> AttributeCreator_Alphanumeric
Note: Alpha Numeric - No spaces or non Alpha/Numeric characters
AttributeCreator_Alphanumeric
    ATTR_TABLE = SET_TO FieldType_AlphaNumeric_Pass = TRUE - Field contains Alphanumeric Values only (no spaces or special characters)
    -> Junction

Bookmark: Validate Boolean value fields
AttributeValidator_13
    TABLE = _attr_value;TYPE;BOOL
    PASSED -> DuplicateFilter_17
    FAILED -> DuplicateFilter_18
DuplicateFilter_17
    INPUT_ORDERED_CHOICE_LOOKUP = NO
    KEYATTR = _attr_name
    PRESERVE_FEATURE_ORDER_LOOKUP = PER_OUTPUT_PORT
    INPUT_ORDERED_CHOICE = No
    UNIQUE -> FeatureMerger_20 [REQUESTOR]
DuplicateFilter_18
    INPUT_ORDERED_CHOICE_LOOKUP = NO
    KEYATTR = _attr_name
    PRESERVE_FEATURE_ORDER_LOOKUP = PER_OUTPUT_PORT
    INPUT_ORDERED_CHOICE = No
    UNIQUE -> FeatureMerger_20 [SUPPLIER]
FeatureMerger_20
    ATTR_ACCUM_MODE = Merge Supplier
    ATTR_CONFLICT_RES_LOOKUP = REQUESTOR_IF_CONFLICT
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> AttributeCreator_Boolean
Note: Boolean
AttributeCreator_Boolean
    ATTR_TABLE = SET_TO Type_Pass_Boolean = TRUE - Contains all Boolean values (1,2,Yes,No)
    -> Junction

Bookmark: Validate Numeric value fields
AttributeValidator_11
    TABLE = _attr_value;TYPE;NUM
    PASSED -> FeatureMerger_2 [REQUESTOR]
    PASSED -> FeatureMerger_22 [SUPPLIER]
    FAILED -> FeatureMerger_2 [SUPPLIER]
    FAILED -> FeatureMerger_22 [REQUESTOR]
FeatureMerger_2
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(_attr_name) @Value(_attr_name) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    UNMERGED_REQUESTOR -> Junction_20
    UNMERGED_REQUESTOR -> DuplicateFilter
DuplicateFilter
    INPUT_ORDERED_CHOICE_LOOKUP = NO
    KEYATTR = _attr_name
    PRESERVE_FEATURE_ORDER_LOOKUP = PER_OUTPUT_PORT
    INPUT_ORDERED_CHOICE = No
    UNIQUE -> AttributeCreator_Numeric
Note: Numeric
AttributeCreator_Numeric
    ATTR_TABLE = SET_TO FieldType_Numeric_Pass = TRUE - one or more attributes contain Numeric Only Values
    -> Junction_21
    -> Junction_19
Note: FeatureMerger_Text_Strings : Supplier
Junction_19
    -> Junction_22
AttributeValidator_12
    TABLE = _attr_value;TYPE;DOUBLE
    PASSED -> DuplicateFilter_13
    FAILED -> DuplicateFilter_26
DuplicateFilter_13
    INPUT_ORDERED_CHOICE_LOOKUP = NO
    KEYATTR = _attr_name
    PRESERVE_FEATURE_ORDER_LOOKUP = PER_OUTPUT_PORT
    INPUT_ORDERED_CHOICE = No
    UNIQUE -> FeatureMerger_19 [REQUESTOR]
DuplicateFilter_26
    INPUT_ORDERED_CHOICE_LOOKUP = NO
    KEYATTR = _attr_name
    PRESERVE_FEATURE_ORDER_LOOKUP = PER_OUTPUT_PORT
    INPUT_ORDERED_CHOICE = No
    UNIQUE -> FeatureMerger_19 [SUPPLIER]
FeatureMerger_19
    ATTR_ACCUM_MODE = Merge Supplier
    ATTR_CONFLICT_RES_LOOKUP = REQUESTOR_IF_CONFLICT
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> DuplicateFilter_2
DuplicateFilter_2
    INPUT_ORDERED_CHOICE_LOOKUP = NO
    KEYATTR = _attr_name
    PRESERVE_FEATURE_ORDER_LOOKUP = PER_OUTPUT_PORT
    INPUT_ORDERED_CHOICE = No
    UNIQUE -> AttributeCreator_70
Note: Double
AttributeCreator_70
    ATTR_TABLE:
      SET_TO FieldType_Double_Pass = TRUE - one or more attributes contain Decimal Double values
      SET_TO FieldType_Boolean_Pass = FALSE
      SET_TO FieldType_Integer_Pass = FALSE
    -> Junction_21
AttributeValidator_14
    TABLE = _attr_value;TYPE;INT
    PASSED -> DuplicateFilter_14
    FAILED -> DuplicateFilter_15
DuplicateFilter_14
    INPUT_ORDERED_CHOICE_LOOKUP = NO
    KEYATTR = _attr_name
    PRESERVE_FEATURE_ORDER_LOOKUP = PER_OUTPUT_PORT
    INPUT_ORDERED_CHOICE = No
    UNIQUE -> FeatureMerger_21 [REQUESTOR]
DuplicateFilter_15
    INPUT_ORDERED_CHOICE_LOOKUP = NO
    KEYATTR = _attr_name
    PRESERVE_FEATURE_ORDER_LOOKUP = PER_OUTPUT_PORT
    INPUT_ORDERED_CHOICE = No
    UNIQUE -> FeatureMerger_21 [SUPPLIER]
FeatureMerger_21
    ATTR_ACCUM_MODE = Merge Supplier
    ATTR_CONFLICT_RES_LOOKUP = REQUESTOR_IF_CONFLICT
    GROUP_BY = _attr_name
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> AttributeCreator_72
Note: Integar
AttributeCreator_72
    ATTR_TABLE:
      SET_TO FieldType_Integer_Pass = TRUE - one or more attributes contain Integar values
      SET_TO FieldType_Double_Pass = TRUE - one or more attributes contain Non-Decimal Double values
    -> Junction_21
AttributeValidator_17
    TABLE = _attr_value;TYPE;DATE
    PASSED -> FeatureMerger_26 [REQUESTOR]
    FAILED -> FeatureMerger_26 [SUPPLIER]
FeatureMerger_26
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(_attr_name) @Value(_attr_name) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    UNMERGED_REQUESTOR -> DuplicateFilter_21
DuplicateFilter_21
    INPUT_ORDERED_CHOICE_LOOKUP = NO
    KEYATTR = _attr_name
    PRESERVE_FEATURE_ORDER_LOOKUP = PER_OUTPUT_PORT
    INPUT_ORDERED_CHOICE = No
    UNIQUE -> AttributeCreator_Date_Field
Note: Date field
AttributeCreator_Date_Field
    ATTR_TABLE = SET_TO FieldType_Date_Pass = TRUE - one or more attributes contain valid Date Values
    -> Junction_21
Note: Numeric Output
Junction_21
    -> Junction_23

Bookmark: Validate Text Strings
FeatureMerger_Text_Strings_2
    ATTR_ACCUM_MODE = Merge Supplier
    ATTR_CONFLICT_RES_LOOKUP = REQUESTOR_IF_CONFLICT
    GROUP_BY = _attr_name
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> AttributeValidator_2
    UNMERGED_REQUESTOR -> AttributeValidator_3
    UNMERGED_REQUESTOR -> AttributeValidator_4
    UNMERGED_REQUESTOR -> AttributeValidator_5
AttributeValidator_5
    TABLE = _attr_name;CASE;FULL_TITLE
    PASSED -> DuplicateFilter_10
    FAILED -> DuplicateFilter_11
DuplicateFilter_10
    INPUT_ORDERED_CHOICE_LOOKUP = NO
    KEYATTR = _attr_name
    PRESERVE_FEATURE_ORDER_LOOKUP = PER_OUTPUT_PORT
    INPUT_ORDERED_CHOICE = No
    UNIQUE -> FeatureMerger_6 [REQUESTOR]
DuplicateFilter_11
    INPUT_ORDERED_CHOICE_LOOKUP = NO
    KEYATTR = _attr_name
    PRESERVE_FEATURE_ORDER_LOOKUP = PER_OUTPUT_PORT
    INPUT_ORDERED_CHOICE = No
    UNIQUE -> FeatureMerger_6 [SUPPLIER]
FeatureMerger_6
    ATTR_ACCUM_MODE = Merge Supplier
    ATTR_CONFLICT_RES_LOOKUP = REQUESTOR_IF_CONFLICT
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> AttributeValidator_9
AttributeValidator_9
    TABLE = _attr_value;TYPE;NUM
    FAILED -> AttributeCreator_5
AttributeCreator_5
    ATTR_TABLE = SET_TO FieldTextCase_FullTitle = TRUE - All Text characters are Full Title Case
    -> Junction_4
AttributeValidator_4
    TABLE = _attr_name;CASE;TITLE
    PASSED -> DuplicateFilter_8
    FAILED -> DuplicateFilter_9
DuplicateFilter_8
    INPUT_ORDERED_CHOICE_LOOKUP = NO
    KEYATTR = _attr_name
    PRESERVE_FEATURE_ORDER_LOOKUP = PER_OUTPUT_PORT
    INPUT_ORDERED_CHOICE = No
    UNIQUE -> FeatureMerger_5 [REQUESTOR]
DuplicateFilter_9
    INPUT_ORDERED_CHOICE_LOOKUP = NO
    KEYATTR = _attr_name
    PRESERVE_FEATURE_ORDER_LOOKUP = PER_OUTPUT_PORT
    INPUT_ORDERED_CHOICE = No
    UNIQUE -> FeatureMerger_5 [SUPPLIER]
FeatureMerger_5
    ATTR_ACCUM_MODE = Merge Supplier
    ATTR_CONFLICT_RES_LOOKUP = REQUESTOR_IF_CONFLICT
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> AttributeValidator_8
AttributeValidator_8
    TABLE = _attr_value;TYPE;NUM
    FAILED -> AttributeCreator_4
AttributeCreator_4
    ATTR_TABLE = SET_TO FieldTextCase_Title case = TRUE - All Text characters are Title case
    -> Junction_4
AttributeValidator_3
    TABLE = _attr_value;CASE;LOWER
    PASSED -> DuplicateFilter_6
    FAILED -> DuplicateFilter_7
DuplicateFilter_6
    INPUT_ORDERED_CHOICE_LOOKUP = NO
    KEYATTR = _attr_name
    PRESERVE_FEATURE_ORDER_LOOKUP = PER_OUTPUT_PORT
    INPUT_ORDERED_CHOICE = No
    UNIQUE -> FeatureMerger_4 [REQUESTOR]
DuplicateFilter_7
    INPUT_ORDERED_CHOICE_LOOKUP = NO
    KEYATTR = _attr_name
    PRESERVE_FEATURE_ORDER_LOOKUP = PER_OUTPUT_PORT
    INPUT_ORDERED_CHOICE = No
    UNIQUE -> FeatureMerger_4 [SUPPLIER]
FeatureMerger_4
    ATTR_ACCUM_MODE = Merge Supplier
    ATTR_CONFLICT_RES_LOOKUP = REQUESTOR_IF_CONFLICT
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> AttributeValidator_7
AttributeValidator_7
    TABLE = _attr_value;TYPE;NUM
    FAILED -> AttributeCreator_3
AttributeCreator_3
    ATTR_TABLE = SET_TO FieldTextCase_lowercase = TRUE - All Text characters are lowercase
    -> Junction_4
AttributeValidator_2
    TABLE = _attr_value;CASE;UPPER
    PASSED -> DuplicateFilter_4
    FAILED -> DuplicateFilter_5
DuplicateFilter_4
    INPUT_ORDERED_CHOICE_LOOKUP = NO
    KEYATTR = _attr_name
    PRESERVE_FEATURE_ORDER_LOOKUP = PER_OUTPUT_PORT
    INPUT_ORDERED_CHOICE = No
    UNIQUE -> FeatureMerger_3 [REQUESTOR]
DuplicateFilter_5
    INPUT_ORDERED_CHOICE_LOOKUP = NO
    KEYATTR = _attr_name
    PRESERVE_FEATURE_ORDER_LOOKUP = PER_OUTPUT_PORT
    INPUT_ORDERED_CHOICE = No
    UNIQUE -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    UNMERGED_REQUESTOR -> AttributeValidator_6
AttributeValidator_6
    TABLE = _attr_value;TYPE;NUM
    FAILED -> AttributeCreator_2
AttributeCreator_2
    ATTR_TABLE = SET_TO FieldTextCase_UPPERCASE = TRUE - All Text characters are UPPERCASE
    -> Junction_4
Note: Text Case output
Note: Text Case
Junction_4
    -> Junction_23

Bookmark: Get all Numeric Values
FeatureMerger_22
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(_attr_name) @Value(_attr_name) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    UNMERGED_REQUESTOR -> Junction_20
Junction_20
    -> AttributeValidator_12
    -> AttributeValidator_14
    -> AttributeValidator_17

FME custom transformer NullAttributeCounter
-->
            Calculates the number of elements that contain values or null values per attribute, excluding attributes from the list or attributes that start with a certain prefix. As a result it returns a transposed table with a list of the attribute names 'AttrName' and the counts for 'Null' and 'NotNull' values.
            Input Port
                Input: All features .
            Output Port
                Output: New features are output from this port
                        Attribute name 
                        Description 
                        AttrName
                        Column for the name of the attribute.
                        Null
                        Column with feature count containing null value in the checked attribute.
                        NotNull
                        Column with feature count containing not null value in the checked attribute.
            Parameters
                        Parameter name 
                        Prompt 
                        Description 
                        Optional 
                        AttributesToExclude
                        Attributes to exclude:.
                        Attributes to exclude in the counts.
                        Yes
                        PrefixesToExclude
                        Prefixes to exclude:.
                        Attributes to exclude starting with the list of prefixes (separated by comma).
                        Yes
Calculates the number of elements that contain values or null values per attribute, excluding attributes from the list or attributes that start with a certain prefix. As a result it returns a transposed table with a list of the attribute names 'AttrName' and the counts for 'Null' and 'NotNull' values.

Parameters:
- AttributesToExclude =   # " " Attributes to exclude
- PrefixesToExclude =   # Prefixes to exclude

Input (input)
    -> ParameterFetcher
ParameterFetcher
    ATTR_LIST = _AttributesToExclude {$(AttributesToExclude)} _PrefixesToExclude {$(PrefixesToExclude)}
    -> PythonCaller
PythonCaller
    NEW_ATTRIBUTES = AttrName Null NotNull
    PYTHONSOURCE:
      import fme
      import fmeobjects

      #Based on SchemaSetter transformer
      #Checks if a list entry starts with a certain string
      def StringLikeList(prefixlist,attrlist):
              print(' - Excluding attributes...')
              prefixattrlist = []
              for prefix in prefixlist:
                  if prefix != '':
                      for attr in attrlist:
                          if attr.startswith(prefix):
                              prefixattrlist.append(attr)
              return prefixattrlist


      # Template Function interface:
      # When using this function, make sure its name is set as the value of
      # the 'Class or Function to Process Features' transformer parameter
      def processFeature(feature):
          attlist = feature.getAllAttributeNames()
          pass

      # Template Class Interface:
      # When using this class, make sure its name is set as the value of
      # the 'Class or Function to Process Features' transformer parameter
      class countNullValues(object):
          def __init__(self):
              #Store all the features in one list
              self.featureList = []
              self.mydict = {}
              pass


          def input(self,feature):
              #Add the features in the list
              self.featureList.append(feature)


          def close(self):
              #Get all attribute names
              print(' - Reading attributes...')
              attlist = self.featureList[0].getAllAttributeNames()
              attlist.sort(key=str.casefold)

              #Get attributes names to exclude
              ExcludedAttributes = str(self.featureList[0].getAttribute('_AttributesToExclude')).split(",")
              ExcludedPrefixes = StringLikeList(str(self.featureList[0].getAttribute('_PrefixesToExclude')).split(","),attlist)
              attexc = ExcludedAttributes + ExcludedPrefixes
              attexc.append('_AttributesToExclude')
              attexc.append('_PrefixesToExclude')
              print(' - Attributes to remove:', attexc)

              #Remove attributes from list
              for exc in attexc:
                  if exc != '':
                      attlist.remove(exc)

              #Create the dictionary with the names of the attributes
              for att in attlist:
                  self.mydict[att] = {}

              #Add attributes for counts
              for att in attlist:
                  self.mydict[att]['Null'] = 0
                  self.mydict[att]['NotNull'] = 0

              #Loop with all the features
              print(' - Making statistics...')
              for feature in self.featureList:
                  #Loop through attribute names
                  for att in attlist:
                      #Get the value for the attribute of that feature
                      value = feature.getAttribute(att)
                      #Make counts and update dictionary
                      if value == "" :
                          self.mydict[att]['Null'] = self.mydict[att]['Null'] + 1
                      else:
                          self.mydict[att]['NotNull'] = self.mydict[att]['NotNull'] + 1

              #Transpose the table and create 2 new attributes
              print(' - Transposing table...')
              for att in attlist:
                  feature.setAttribute("AttrName", att)
                  feature.setAttribute("Null", self.mydict[att]['Null'])
                  feature.setAttribute("NotNull", self.mydict[att]['NotNull'])
                  feature.removeAttribute(att)

                  #Export all features to FME
                  self.pyoutput(feature)

              #If you put this here, you are going to export only one feature to FME
              #self.pyoutput(feature)

              pass
    PYTHONSYMBOL = countNullValues
    -> AttributeKeeper
AttributeKeeper
    CREATE_BULK_MODE_FEATURES = NO
    KEEP_ATTRS = AttrName,NotNull,Null
    -> Output (output)
Output (output)

FME custom transformer Esri_AttributeFieldChecker
A rough schema check used to review structure of the attribute table prior to writing to an ESRI/ArcGIS file format (AGOL/FGDB/SHP).
Queries each attribute field and analyzes each field names and values.  Outputs a table with a single record/row for each field name/table column.
Output Attribute Fields
_attr_name
Attribute field name
_attr_value
Attribute value in the field (_attr_name) with the longest character length/count
_Value_MaxCharacterLength
Character count/length of the attribute value with the longest character count (_attr_value)
_FieldName_CharacterLength
Character count/length of the field name value (_attr_name)
_FieldName_AGOLcheck
Pass/ Fail - ArcGIS Online (AGOL) character limit: is the field name length 31 characters or less
Test Condition: @LEFT(VALUE(_attr_name),31)
_FieldName_FGDBcheck
Pass/ Fail - ArcGIS File Geodatabase (FGDB) character limit: is the field name length 64 characters or less
Test Condition: @Left(@Value(_attr_name),64)
_FieldName_SHPcheck
Pass/ Fail - ArcGIS Shapefile (SHP) character limit: is the field name length 10 characters or less
Test Condition: @Left(@Value(_attr_name),10)
_FieldName_AGOLcheck_Trimmed
Field Name value trimmed to 31 characters to meet AGOL limits
_FieldName_FGDBcheck_Trimmed
Field Name value trimmed to 64 characters to meet FGDB limits
_FieldName_SHPcheck_Trimmed
Field Name value trimmed to 10 characters to meet SHP limits
_FieldName_Special Character_Flag
Regular Expression check if field name contains special characters Note: excludes underscores except leading underschores.  In addition to special characters it checks for: leading number.digit character, a leading space character, space character anywhere)
_FieldName_Reserved_Word_Flag
Regular Expression check if field name is a reserved word (MS Access & MS Jet 4.0 reserved words)
FieldType_AlphaNumeric_Pass
Check if all values in the field meet the criteria of an ALPHANUMERIC field
Test Condition: @Value(_attr_value) CONTAINS_REGEX ^.(?=.\d)(?=.[a-zA-Z]).$
FieldType_Alpha_Pass
Check if all values in the field meet the criteria of an ALPHA field
Test Condition: @Value(_attr_value) NOT_TYPE NUM
FieldType_Numeric_Pass
Check if all values in the field meet the criteria of an NUMERIC field
Test Condition: @Value(_attr_value) TYPE NUM
FieldType_Boolean_Pass
Check if all values in the field meet the criteria of an BOOLEAN field
FieldType_Integer_Pass
Check if all values in the field meet the criteria of an INTEGAR field
Test Condition: @Value(_attr_value) TYPE INT
FieldType_Double_Pass
Check if all values in the field meet the criteria of an DOUBLE field
Test Condition: @Value(_attr_value) TYPE DOUBLE
FieldType_NOT_Double-or-Integer_Pass
Check if all values in the field meet the criteria of NOT being a DOUBLE or INTEGAR field
_Contains NULL Values
Field contains one or more NULL values
Test Condition: _attr_value ATTRIBUTE_VALUE_NULL
_Contains Missing Values
Field contains one or more Missing values
Test Condition: _attr_value ATTRIBUTE_IS_MISSING
_DateValue_Simple Date
Field contains date with two or four digit year: "MM/DD/YYYY" or "MM/DD/YY" or "M/DD/YYYY" or "M/DD/YY
Test Condition: @Value(_attr_value) CONTAINS_REGEX ^([0-9]|0[0-9]|1[0-9])\/[0-3][0-9]\/([1-2][0-9]{3}|[0-9]{2})$
_DateValue_Simple Date_YYYYMMDD
Field contains date with four digit year: YYYYMMDD
Test Condition: @Value(_attr_value) CONTAINS_REGEX ^(1|2)([0-9]){3}(0[0-9]|1[1-2])([0-2][0-9]|3[0-1])$
_DateValue_Month in Long Form
Field contains date with the Month in long form (January 12, 2019)
Test Condition: @Value(_attr_value) CONTAINS_REGEX ^(January|February|March|April|May|June|July|August|September|October|November|December) ([0-3][0-9]),\s[1-2][0-9]{3}$
_DateValue_four digit year with time
Field contains date as four digit year with Time:  "MM/DD/YYYY H:MM:SS AM" or "M/DD/YYYY HH:MM:SS PM"  or  "MM/DD/YYYY H:MM AM"  or  "M/DD/YYYY HH:MM PM" 
Test Condition: @Value(_attr_value) CONTAINS_REGEX ^([0-9]|0[0-9]|1[0-2])\/([0-3][0-9])\/[1-2][0-9]{3} ([0-9]|0[0-9]|1[0-2]):(0[0-9]|[0-5][0-9]):?([0-9]){0,2} (AM|PM)$
_DateValue_two digit year with time
Field contains date as two digit year with Time: "MM/DD/YY H:MM:SS AM" or "M/DD/YY HH:MM:SS PM" or  "MM/DD/YY H:MM AM" or "M/DD/YY HH:MM PM" 
Test Condition: @Value(_attr_value) CONTAINS_REGEX ^([0-9]|0[0-9]|1[0-2])\/([0-3][0-9])\/([0-9]{2}) ([0-9]|0[0-9]|1[0-2]):(0[0-9]|[0-5][0-9]):?([0-9]){0,2} (AM|PM)$
_DateValue_Not Esri Date Format
Field does not contain a valid date
Reference Links
ArcGIS field data types
https://desktop.arcgis.com/en/arcmap/latest/manage-data/geodatabases/arcgis-field-data-types.htm
FAQ: What characters should not be used in ArcGIS for field names and table names?
https://support.esri.com/en/technical-article/000005588
Learn about Access reserved words and symbols
https://support.office.com/en-us/article/learn-about-access-reserved-words-and-symbols-ae9d9ada-3255-4b12-91a9-f855bdd9c5a2#__toc262648754
List of reserved words in Access 2002 and in later versions of Access
https://support.microsoft.com/en-us/help/286335/list-of-reserved-words-in-access-2002-and-in-later-versions-of-access
List of Microsoft Jet 4.0 reserved words
https://support.microsoft.com/en-us/help/321266/list-of-microsoft-jet-4-0-reserved-words
FME Standard Date/Time Format
https://docs.safe.com/fme/html/FME_Desktop_Documentation/FME_ReadersWriters/!Transformer_Parameters/standard_fme_date_time_format.htm

Need_to_know_Max_Field_Value_&_Length (input)
    -> AttributeExploder
Note: Explode all the attributes and ignore all the numeric and FME fields.
Note: AttributeExploder [AttributeExploder] / Parameters: / Exploding Type: Features / Attribute Name Label: _attr_name / Attribute Value Label: _attr_value / Keep Geometry: No / Keep Attributes: No
AttributeExploder
    ATTR_NAME_LABEL = _attr_name
    ATTR_VALUE_LABEL = _attr_value
    EXPLODING_TYPE_LOOKUP = EXPLODE_AS_FEATURES
    KEEP_ATTRIBUTES = No
    KEEP_GEOMETRY = No
    EXPLODING_TYPE = Features
    -> DuplicateFilter_16
Note: Pivot Attribute Field Names as values into _attr_name ; Retrieve the value with the longest chracter count/length for each attribute field as _attr_values
DuplicateFilter_16
    INPUT_ORDERED_CHOICE_LOOKUP = NO
    KEYATTR = _attr_name _attr_value
    PRESERVE_FEATURE_ORDER_LOOKUP = PER_OUTPUT_PORT
    INPUT_ORDERED_CHOICE = No
    UNIQUE -> AttributeDataTypeCheck_2 [DuplicateFilter_6_Input]
    UNIQUE -> StringLengthCalculator_4
    UNIQUE -> TestFilter_17
    UNIQUE -> Junction_8 [off]
Note: Evaluate Field Data Types
Note: Esri Field Name Length Check
Note: Check Attribute Field values for Data Type consistancy
Note: Check Field Name for special characters/reserved words
AttributeDataTypeCheck_2
    _ATTR_NAME = @Value(_attr_name)
    _ATTR_VALUE = @Value(_attr_value)
    Output:_Attribute_Field_Data_Type_Check -> FeatureMerger [REQUESTOR]
DuplicateFilter_2
    INPUT_ORDERED_CHOICE_LOOKUP = NO
    KEYATTR = _attr_name _DateValue_WriteToFGDB_YYYYMMDDHHMMSS FieldType_Date_Pass _DateValue_WriteToAGOL_YYYYMMDDHHMMSSs _DateValue_WriteToAGOL_YYYYMMDD _Contains Empty Values _DateValue_WriteToFGDB_[Datetime][UTC offset]_YYYYMMDDHHMMSSs(+/-)hh:mm _DateValue_Not a valid Date Field _DateValue_WriteToShapeFile _Contains NULL Values _DateValue_WriteToShapeFile_YYYYMMDD _DateValue_WriteToShapeFile_YYYYMMDDHHMMSS _DateValue_WriteToFGDB_YYYYMMDD _DateValue_WriteToAGOL_[Datetime][UTC offset]_YYYYMMDDHHMMSSs(+/-)hh:mm _DateValue_WriteToAGOL_YYYYMMDDHHMMSS _DateValue_WriteToFGDB_YYYYMMDDHHMMSSs
    PRESERVE_FEATURE_ORDER_LOOKUP = PER_OUTPUT_PORT
    INPUT_ORDERED_CHOICE = No
    UNIQUE -> Aggregator_4
Aggregator_4
    ACCUM_ATTRS_NAME = Merge Incoming Attributes
    CONCAT_ATTRS = _DateValue_WriteToFGDB_YYYYMMDDHHMMSS FieldType_Date_Pass _DateValue_WriteToAGOL_YYYYMMDDHHMMSSs _DateValue_WriteToAGOL_YYYYMMDD "_Contains Empty Values" "_DateValue_WriteToFGDB_[Datetime][UTC offset]_YYYYMMDDHHMMSSs(+/-)hh:mm" "_DateValue_Not a valid Date Field" _DateValue_WriteToShapeFile "_Contains NULL Values" _DateValue_WriteToShapeFile_YYYYMMDD _DateValue_WriteToShapeFile_YYYYMMDDHHMMSS _DateValue_WriteToFGDB_YYYYMMDD "_DateValue_WriteToAGOL_[Datetime][UTC offset]_YYYYMMDDHHMMSSs(+/-)hh:mm" _DateValue_WriteToAGOL_YYYYMMDDHHMMSS _DateValue_WriteToFGDB_YYYYMMDDHHMMSSs
    GROUP_BY = _attr_name
    MODE = Attributes Only
    SEP = ,
    AGGREGATE -> StringReplacer_2
StringReplacer_2
    CASE = NO
    FIND_TEXT = ,
    NO_MATCH = _FME_NO_OP_
    REGEXP = NO
    SRC_ATTRS = _DateValue_WriteToFGDB_YYYYMMDDHHMMSS,FieldType_Date_Pass,_DateValue_WriteToAGOL_YYYYMMDDHHMMSSs,_DateValue_WriteToAGOL_YYYYMMDD,_Contains Empty Values,_DateValue_WriteToFGDB_[Datetime][UTC offset]_YYYYMMDDHHMMSSs(+/-)hh:mm,_DateValue_Not a valid Date Field,_DateValue_WriteToShapeFile,_Contains NULL Values,_DateValue_WriteToShapeFile_YYYYMMDD,_DateValue_WriteToShapeFile_YYYYMMDDHHMMSS,_DateValue_WriteToFGDB_YYYYMMDD,_DateValue_WriteToAGOL_[Datetime][UTC offset]_YYYYMMDDHHMMSSs(+/-)hh:mm,_DateValue_WriteToAGOL_YYYYMMDDHHMMSS,_DateValue_WriteToFGDB_YYYYMMDDHHMMSSs
    -> FeatureMerger [SUPPLIER]
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(_attr_name) @Value(_attr_name) AUTO
    MERGE_TYPE = Attributes Only
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGED -> FeatureMerger_8 [SUPPLIER]
FeatureMerger_8
    ATTR_ACCUM_MODE = Merge Supplier
    ATTR_CONFLICT_RES_LOOKUP = REQUESTOR_IF_CONFLICT
    IGNORE_NULLS = No
    JOIN_KEYS = @Value(_attr_name) @Value(_attr_name) AUTO
    MERGE_TYPE = Attributes Only
    PROCESS_DUPS = NO
    REJECT_NULL_MISSING_KEYS = No
    SUPPLIERS_FIRST = No
    ATTR_CONFLICT_RES = Use Requestor
    MERGED -> AttributeManager_3
AttributeManager_3
    ATTR_TABLE:
      REMOVE _length
      RENAME_SET_VALUE _max > _Value_MaxCharacterLength
      RENAME_SET_VALUE _FieldName_length > _FieldName_CharacterLength
      RENAME_SET_VALUE _FieldName_Special Character > _FieldName_Special Character_Flag
      RENAME_SET_VALUE _FieldName_Reserved_Word > _FieldName_Reserved_Word_Flag
      REMOVE FieldType_Boolean_Pass
    -> TestFilter_4
TestFilter_4
    DEFAULT_VALUE = <UNFILTERED>
    TEST_LIST:
      "BOOL_OP,AND,COMPOSITE_TEST,""""""1 AND 2 AND 3 AND 4"""""",TEST_CLAUSE,CASE_SENSITIVE_TEST @Value(_attr_name) NOT_BEGINS_WITH fme_
      CASE_SENSITIVE_TEST @Value(_attr_name) NOT_BEGINS_WITH multi_
      CASE_INSENSITIVE_TEST @Value(_attr_name) NOT_ENDS_WITH _alias
      CASE_INSENSITIVE_TEST @Value(_attr_name) NOT_BEGINS_WITH geodb_",Primary Field = @Value(_attr_value) NOT_fme_ or multi_ or _alias,"BOOL_OP,AND,COMPOSITE_TEST,""""""1"""""",TEST_CLAUSE,CASE_SENSITIVE_TEST @Value(_attr_name) BEGINS_WITH multi_",Prefix: Multi_,"BOOL_OP,AND,COMPOSITE_TEST,""""""1"""""",TEST_CLAUSE,CASE_SENSITIVE_TEST @Value(_attr_name) BEGINS_WITH fme_",Prefix: fme_,"BOOL_OP,OR,COMPOSITE_TEST,""""""1"""""",TEST_CLAUSE,CASE_INSENSITIVE_TEST @Value(_attr_name) BEGINS_WITH geodb_",Prefix: geodb_,"BOOL_OP,OR,COMPOSITE_TEST,""""""1"""""",TEST_CLAUSE,CASE_INSENSITIVE_TEST @Value(_attr_name) ENDS_WITH _alias",Suffix: _alias
    Primary Field = @Value(_attr_value) NOT_fme_ or multi_ or _alias -> Output:_Primary_Fields (output)
    Prefix: Multi_ -> Output:_Prefixed_with_Multi_ (output)
    Prefix: fme_ -> Output:_Prefixed_with_fme_ (output)
    Prefix: geodb_ -> Output:_Prefixed_with_geodb_ (output)
    Suffix: _alias -> Output:_Suffixed_with__alias (output)
Output:_Primary_Fields (output)
Output:_Prefixed_with_Multi_ (output)
Output:_Prefixed_with_fme_ (output)
Output:_Prefixed_with_geodb_ (output)
Output:_Suffixed_with__alias (output)

Bookmark: Retrieve the value with the longest chracter count/length for each attribute field
Note: StringLengthCalculator_4 [StringLengthCalculator] / Parameters: / Source Attribute: _attr_value / String Length Attribute: _length
StringLengthCalculator_4
    LENGTH_ATTR = _length
    SRC_ATTR = _attr_value
    -> StatisticsCalculator_3
Note: Group by _attr_name, / and calculate the max length
StatisticsCalculator_3
    COMPUTE_HISTOGRAM = NO
    GROUP_BY = _attr_name
    MAX_ATTR = _max
    PREPEND_ATTR_NAME = No
    STATS_ATTRS = _length
    PREPEND_ATTR_NAME_CHOICE = For multiple results only
    COMPLETE -> Tester_3
Note: Tester_3 [Tester] / Test Clauses: Left ValueOperatorRight Value@Value(_length)=@Value(_max)
Note: Select the values that have the max length, and pick the first one
Tester_3
    BOOL_OP = OR
    TEST_CLAUSE = TEST @Value(_length) = @Value(_max)
    TEST_MODE = TEST
    PASSED -> Sampler_7
Sampler_7
    GROUP_BY = _attr_name
    MODE = ORIGINAL
    RATE = 1
    SAMPLE_TYPE_MULTIPLIER = -1
    SAMPLE_MODE = No
    SAMPLE_TYPE_LONG = First N Features
    SAMPLED -> Sorter
Note: Sort the list of attributes alphatically or longest first
Note: Sorter [Sorter] / Sort By: AttributeAlpha/NumOrder_attr_nameAlphabeticAscending
Sorter
    SORT_PARM = _attr_name ALPHA ASCENDING
    SORTED -> StringLengthCalculator_2

Bookmark: Esri Field Name Length Check
StringLengthCalculator_2
    LENGTH_ATTR = _FieldName_length
    SRC_ATTR = _attr_name
    -> AttributeCreator
AttributeCreator
    ATTR_TABLE:
      SET_TO _FieldName_FGDBcheck = FME_CONDITIONAL:DEFAULT_VALUE'_FME_NO_OP_'BOOL_OP;OR;COMPOSITE_TEST;1;TEST @Value(_FieldName_length) <= 64'Pass - Field Name length is 64 characters or less'BOOL_OP;OR;COMPOSITE_TEST;1;TEST @Value(_FieldName_length) > 64'FAIL - Field Name lentgh greater than 64 characters'FME_NUM_CONDITIONS3___
      SET_TO _FieldName_AGOLcheck = FME_CONDITIONAL:DEFAULT_VALUE'_FME_NO_OP_'BOOL_OP;OR;COMPOSITE_TEST;1;TEST @Value(_FieldName_length) <= 31'Pass - Field Name length is 31 characters or less'BOOL_OP;OR;COMPOSITE_TEST;1;TEST @Value(_FieldName_length) > 31'FAIL - Field Name lentgh greater than 31 characters'FME_NUM_CONDITIONS3___
      SET_TO _FieldName_SHPcheck = FME_CONDITIONAL:DEFAULT_VALUE'_FME_NO_OP_'BOOL_OP;OR;COMPOSITE_TEST;1;TEST @Value(_FieldName_length) <= 10'Pass - Field Name length is 10 characters or less'BOOL_OP;OR;COMPOSITE_TEST;1;TEST @Value(_FieldName_length) > 10'FAIL - Field Name lentgh greater than 10 characters'FME_NUM_CONDITIONS3___
      SET_TO _FieldName_FGDBcheck_Trimmed = @Left(@Value(_attr_name),64)
      SET_TO _FieldName_AGOLcheck_Trimmed = @Left(@Value(_attr_name),31)
      SET_TO _FieldName_SHPcheck_Trimmed = @Left(@Value(_attr_name),10)
    -> TestFilter_7
    -> TestFilter_8
    -> TestFilter_6

Bookmark: Check Field Name for special characters/reserved words
TestFilter_7
    DEFAULT_VALUE = <UNFILTERED>
    TEST_LIST = "BOOL_OP,OR,COMPOSITE_TEST,""""""1"""""",TEST_CLAUSE,CASE_SENSITIVE_TEST @Value(_attr_name) CONTAINS_REGEX ^(ADD|Add|add|ALL|All|all|ALPHANUMERIC|Alphanumeric|alphanumeric|ALTER|Alter|alter|AND|And|and|ANY|Any|any|APPLICATION|Application|application|AS|As|as|ASC|Asc|asc|ASSISTANT|Assistant|assistant|AUTOINCREMENT|Autoincrement|autoincrement|AVG|Avg|avg|BETWEEN|Between|between|BINARY|Binary|binary|BIT|Bit|bit|BOOLEAN|Boolean|boolean|BY|By|by|BYTE|Byte|byte|CHAR, CHARACTER|Char, Character|char, character|COLUMN|Column|column|COMPACTDATABASE|Compactdatabase|compactdatabase|CONSTRAINT|Constraint|constraint|CONTAINER|Container|container|COUNT|Count|count|COUNTER|Counter|counter|CREATE|Create|create|CREATEDATABASE|Createdatabase|createdatabase|CREATEFIELD|Createfield|createfield|CREATEGROUP|Creategroup|creategroup|CREATEINDEX|Createindex|createindex|CREATEOBJECT|Createobject|createobject|CREATEPROPERTY|Createproperty|createproperty|CREATERELATION|Createrelation|createrelation|CREATETABLEDEF|Createtabledef|createtabledef|CREATEUSER|Createuser|createuser|CREATEWORKSPACE|Createworkspace|createworkspace|CURRENCY|Currency|currency|CURRENTUSER|Currentuser|currentuser|DATABASE|Database|database|DATE|Date|date|DATETIME|Datetime|datetime|DELETE|Delete|delete|DESC|Desc|desc|DESCRIPTION|Description|description|DISALLOW|Disallow|disallow|DISTINCT|Distinct|distinct|DISTINCTROW|Distinctrow|distinctrow|DOCUMENT|Document|document|DOUBLE|Double|double|DROP|Drop|drop|ECHO|Echo|echo|ELSE|Else|else|END|End|end|EQV|Eqv|eqv|ERROR|Error|error|EXISTS|Exists|exists|EXIT|Exit|exit|FALSE|False|false|FIELD, FIELDS|Field, Fields|field, fields|FILLCACHE|Fillcache|fillcache|FLOAT, FLOAT4, FLOAT8|Float, Float4, Float8|float, float4, float8|FOREIGN|Foreign|foreign|FORM, FORMS|Form, Forms|form, forms|FROM|From|from|FULL|Full|full|FUNCTION|Function|function|GENERAL|General|general|GETOBJECT|Getobject|getobject|GETOPTION|Getoption|getoption|GOTOPAGE|Gotopage|gotopage|GROUP|Group|group|GROUP BY|Group By|group by|GUID|Guid|guid|HAVING|Having|having|IDLE|Idle|idle|IEEEDOUBLE, IEEESINGLE|Ieeedouble, Ieeesingle|ieeedouble, ieeesingle|IF|If|if|IGNORE|Ignore|ignore|IMP|Imp|imp|IN|In|in|INDEX|Index|index|INDEX, INDEXES|Index, Indexes|index, indexes|INNER|Inner|inner|INSERT|Insert|insert|INSERTTEXT|Inserttext|inserttext|INT, INTEGER, INTEGER1, INTEGER2, INTEGER4|Int, Integer, Integer1, Integer2, Integer4|int, integer, integer1, integer2, integer4|INTO|Into|into|IS|Is|is|JOIN|Join|join|KEY|Key|key|LASTMODIFIED|Lastmodified|lastmodified|LEFT|Left|left|LEVEL|Level|level|LIKE|Like|like|LOGICAL, LOGICAL1|Logical, Logical1|logical, logical1|LONG, LONGBINARY, LONGTEXT|Long, Longbinary, Longtext|long, longbinary, longtext|MACRO|Macro|macro|MATCH|Match|match|MAX, MIN, MOD|Max, Min, Mod|max, min, mod|MEMO|Memo|memo|MODULE|Module|module|MONEY|Money|money|MOVE|Move|move|NAME|Name|name|NEWPASSWORD|Newpassword|newpassword|NO|No|no|NOT|Not|not|NOTE|Note|note|NULL|Null|null|NUMBER, NUMERIC|Number, Numeric|number, numeric|OBJECT|Object|object|OFF|Off|off|OLEOBJECT|Oleobject|oleobject|ON|On|on|OPENRECORDSET|Openrecordset|openrecordset|OPTION|Option|option|OR|Or|or|ORDER|Order|order|ORIENTATION|Orientation|orientation|OUTER|Outer|outer|OWNERACCESS|Owneraccess|owneraccess|PARAMETER|Parameter|parameter|PARAMETERS|Parameters|parameters|PARTIAL|Partial|partial|PERCENT|Percent|percent|PIVOT|Pivot|pivot|PRIMARY|Primary|primary|PROCEDURE|Procedure|procedure|PROPERTY|Property|property|QUERIES|Queries|queries|QUERY|Query|query|QUIT|Quit|quit|REAL|Real|real|RECALC|Recalc|recalc|RECORDSET|Recordset|recordset|REFERENCES|References|references|REFRESH|Refresh|refresh|REFRESHLINK|Refreshlink|refreshlink|REGISTERDATABASE|Registerdatabase|registerdatabase|RELATION|Relation|relation|REPAINT|Repaint|repaint|REPAIRDATABASE|Repairdatabase|repairdatabase|REPORT|Report|report|REPORTS|Reports|reports|REQUERY|Requery|requery|RIGHT|Right|right|SCREEN|Screen|screen|SECTION|Section|section|SELECT|Select|select|SET|Set|set|SETFOCUS|Setfocus|setfocus|SETOPTION|Setoption|setoption|SHORT|Short|short|SINGLE|Single|single|SMALLINT|Smallint|smallint|SOME|Some|some|SQL|Sql|sql|STDEV, STDEVP|Stdev, Stdevp|stdev, stdevp|STRING|String|string|SUM|Sum|sum|TABLE|Table|table|TABLEDEF, TABLEDEFS|Tabledef, Tabledefs|tabledef, tabledefs|TABLEID|Tableid|tableid|TEXT|Text|text|TIME, TIMESTAMP|Time, Timestamp|time, timestamp|TOP|Top|top|TRANSFORM|Transform|transform|TRUE|True|true|TYPE|Type|type|UNION|Union|union|UNIQUE|Unique|unique|UPDATE|Update|update|USER|User|user|VALUE|Value|value|VALUES|Values|values|VAR, VARP|Var, Varp|var, varp|VARBINARY, VARCHAR|Varbinary, Varchar|varbinary, varchar|VERSION|Version|version|WHERE|Where|where|WITH|With|with|WORKSPACE|Workspace|workspace|XOR|Xor|xor|YEAR|Year|year|YES|Yes|yes|YESNO|Yesno|yesno)$",Field Name - MS Acces Reserved Word
    Field Name - MS Acces Reserved Word -> AttributeCreator_3
AttributeCreator_3
    ATTR_TABLE = SET_TO _FieldName_Reserved_Word = MS Access
    -> Aggregator
TestFilter_8
    DEFAULT_VALUE = <UNFILTERED>
    TEST_LIST = "BOOL_OP,OR,COMPOSITE_TEST,""""""1"""""",TEST_CLAUSE,CASE_SENSITIVE_TEST @Value(_attr_name) CONTAINS_REGEX ^(ABSOLUTE|Absolute|absolute|ACTION|Action|action|ADD|Add|add|ADMINDB|Admindb|admindb|ALL|All|all|ALLOCATE|Allocate|allocate|ALPHANUMERIC|Alphanumeric|alphanumeric|ALTER|Alter|alter|AND|And|and|ANY|Any|any|ARE|Are|are|AS|As|as|ASC|Asc|asc|ASSERTION|Assertion|assertion|AT|At|at|AUTHORIZATION|Authorization|authorization|AUTOINCREMENT|Autoincrement|autoincrement|AVG|Avg|avg|BAND|Band|band|BEGIN|Begin|begin|BETWEEN|Between|between|BINARY|Binary|binary|BIT|Bit|bit|BIT_LENGTH|Bit_Length|bit_length|BNOT|Bnot|bnot|BOR|Bor|bor|BOTH|Both|both|BXOR|Bxor|bxor|BY|By|by|BYTE|Byte|byte|CASCADE|Cascade|cascade|CASCADED|Cascaded|cascaded|CASE|Case|case|CAST|Cast|cast|CATALOG|Catalog|catalog|CHAR|Char|char|CHAR_LENGTH|Char_Length|char_length|CHARACTER|Character|character|CHARACTER_LENGTH|Character_Length|character_length|CHECK|Check|check|CLOSE|Close|close|COALESCE|Coalesce|coalesce|COLLATE|Collate|collate|COLLATION|Collation|collation|COLUMN|Column|column|COMMIT|Commit|commit|COMP|Comp|comp|COMPRESSION|Compression|compression|CONNECT|Connect|connect|CONNECTION|Connection|connection|CONSTRAINT|Constraint|constraint|CONSTRAINTS|Constraints|constraints|CONTAINER|Container|container|CONTINUE|Continue|continue|CONVERT|Convert|convert|CORRESPONDING|Corresponding|corresponding|COUNT|Count|count|COUNTER|Counter|counter|CREATE|Create|create|CREATEDB|Createdb|createdb|CROSS|Cross|cross|CURRENCY|Currency|currency|CURRENT|Current|current|CURRENT_DATE|Current_Date|current_date|CURRENT_TIME|Current_Time|current_time|CURRENT_TIMESTAMP|Current_Timestamp|current_timestamp|CURRENT_USER|Current_User|current_user|CURSOR|Cursor|cursor|DATABASE|Database|database|DATE|Date|date|DATETIME|Datetime|datetime|DAY|Day|day|DEALLOCATE|Deallocate|deallocate|DEC|Dec|dec|DECIMAL|Decimal|decimal|DECLARE|Declare|declare|DEFAULT|Default|default|DEFERRABLE|Deferrable|deferrable|DEFERRED|Deferred|deferred|DELETE|Delete|delete|DESC|Desc|desc|DESCRIBE|Describe|describe|DESCRIPTOR|Descriptor|descriptor|DIAGNOSTICS|Diagnostics|diagnostics|DISALLOW|Disallow|disallow|DISCONNECT|Disconnect|disconnect|DISTINCT|Distinct|distinct|DOMAIN|Domain|domain|DOUBLE|Double|double|DROP|Drop|drop|ELSE|Else|else|END|End|end|END-EXEC|End-Exec|end-exec|ESCAPE|Escape|escape|EXCEPT|Except|except|EXCEPTION|Exception|exception|EXCLUSIVECONNECT|Exclusiveconnect|exclusiveconnect|EXEC|Exec|exec|EXECUTE|Execute|execute|EXISTS|Exists|exists|EXTERNAL|External|external|EXTRACT|Extract|extract|False|false|FETCH|Fetch|fetch|FIRST|First|first|FLOAT|Float|float|FLOAT4|Float4|float4|FLOAT8|Float8|float8|FOR|For|for|FOREIGN|Foreign|foreign|FOUND|Found|found|FROM|From|from|FULL|Full|full|GENERAL|General|general|GET|Get|get|GLOBAL|Global|global|GO|Go|go|GOTO|Goto|goto|GRANT|Grant|grant|GROUP|Group|group|GUID|Guid|guid|HAVING|Having|having|HOUR|Hour|hour|IDENTITY|Identity|identity|IEEEDOUBLE|Ieeedouble|ieeedouble|IEEESINGLE|Ieeesingle|ieeesingle|IGNORE|Ignore|ignore|IMAGE|Image|image|IMMEDIATE|Immediate|immediate|IN|In|in|INDEX|Index|index|INDICATOR|Indicator|indicator|INHERITABLE|Inheritable|inheritable|INITIALLY|Initially|initially|INNER|Inner|inner|INPUT|Input|input|INSENSITIVE|Insensitive|insensitive|INSERT|Insert|insert|INT|Int|int|INTEGER|Integer|integer|INTEGER1|Integer1|integer1|INTEGER2|Integer2|integer2|INTEGER4|Integer4|integer4|INTERSECT|Intersect|intersect|INTERVAL|Interval|interval|INTO|Into|into|IS|Is|is|ISOLATION|Isolation|isolation|JOIN|Join|join|KEY|Key|key|LANGUAGE|Language|language|LAST|Last|last|LEADING|Leading|leading|LEFT|Left|left|LEVEL|Level|level|LIKE|Like|like|LOCAL|Local|local|LOGICAL|Logical|logical|LOGICAL1|Logical1|logical1|LONG|Long|long|LONGBINARY|Longbinary|longbinary|LONGCHAR|Longchar|longchar|LONGTEXT|Longtext|longtext|LOWER|Lower|lower|MATCH|Match|match|MAX|Max|max|MEMO|Memo|memo|MIN|Min|min|MINUTE|Minute|minute|MODULE|Module|module|MONEY|Money|money|MONTH|Month|month|NAMES|Names|names|NATIONAL|National|national|NATURAL|Natural|natural|NCHAR|Nchar|nchar|NEXT|Next|next|NO|No|no|NOT|Not|not|NOTE|Note|note|NULL|Null|null|NULLIF|Nullif|nullif|NUMBER|Number|number|NUMERIC|Numeric|numeric|OBJECT|Object|object|OCTET_LENGTH|Octet_Length|octet_length|OF|Of|of|OLEOBJECT|Oleobject|oleobject|ON|On|on|ONLY|Only|only|OPEN|Open|open|OPTION|Option|option|OR|Or|or|ORDER|Order|order|OUTER|Outer|outer|OUTPUT|Output|output|OVERLAPS|Overlaps|overlaps|OWNERACCESS|Owneraccess|owneraccess|PAD|Pad|pad|PARAMETERS|Parameters|parameters|PARTIAL|Partial|partial|PASSWORD|Password|password|PERCENT|Percent|percent|PIVOT|Pivot|pivot|POSITION|Position|position|PRECISION|Precision|precision|PREPARE|Prepare|prepare|PRESERVE|Preserve|preserve|PRIMARY|Primary|primary|PRIOR|Prior|prior|PRIVILEGES|Privileges|privileges|PROC|Proc|proc|PROCEDURE|Procedure|procedure|PUBLIC|Public|public|READ|Read|read|REAL|Real|real|REFERENCES|References|references|RELATIVE|Relative|relative|RESTRICT|Restrict|restrict|REVOKE|Revoke|revoke|RIGHT|Right|right|ROLLBACK|Rollback|rollback|ROWS|Rows|rows|SCHEMA|Schema|schema|SCROLL|Scroll|scroll|SECOND|Second|second|SECTION|Section|section|SELECT|Select|select|SELECTSCHEMA|Selectschema|selectschema|SELECTSECURITY|Selectsecurity|selectsecurity|SESSION|Session|session|SESSION_USER|Session_User|session_user|SET|Set|set|SHORT|Short|short|SINGLE|Single|single|SIZE|Size|size|SMALLINT|Smallint|smallint|SOME|Some|some|SPACE|Space|space|SQL|Sql|sql|SQLCODE|Sqlcode|sqlcode|SQLERROR|Sqlerror|sqlerror|SQLSTATE|Sqlstate|sqlstate|STRING|String|string|SUBSTRING|Substring|substring|SUM|Sum|sum|SYSTEM_USER|System_User|system_user|TABLE|Table|table|TABLEID|Tableid|tableid|TEMPORARY|Temporary|temporary|TEXT|Text|text|THEN|Then|then|TIME|Time|time|TIMESTAMP|Timestamp|timestamp|TIMEZONE_HOUR|Timezone_Hour|timezone_hour|TIMEZONE_MINUTE|Timezone_Minute|timezone_minute|TO|To|to|TOP|Top|top|TRAILING|Trailing|trailing|TRANSACTION|Transaction|transaction|TRANSFORM|Transform|transform|TRANSLATE|Translate|translate|TRANSLATION|Translation|translation|TRIM|Trim|trim|True|true|UNION|Union|union|UNIQUE|Unique|unique|UNIQUEIDENTIFIER|Uniqueidentifier|uniqueidentifier|UNKNOWN|Unknown|unknown|UPDATE|Update|update|UPDATEIDENTITY|Updateidentity|updateidentity|UPDATEOWNER|Updateowner|updateowner|UPDATESECURITY|Updatesecurity|updatesecurity|UPPER|Upper|upper|USAGE|Usage|usage|USER|User|user|USING|Using|using|VALUE|Value|value|VALUES|Values|values|VARBINARY|Varbinary|varbinary|VARCHAR|Varchar|varchar|VARYING|Varying|varying|VIEW|View|view|WHEN|When|when|WHENEVER|Whenever|whenever|WHERE|Where|where|WITH|With|with|WORK|Work|work|WRITE|Write|write|YEAR|Year|year|YESNO|Yesno|yesno|ZONE|Zone|zone|FALSE|False|false|TRUE|True|true)$",Field Name - Jet 4.0 Reserved Word
    Field Name - Jet 4.0 Reserved Word -> AttributeCreator_2
AttributeCreator_2
    ATTR_TABLE = SET_TO _FieldName_Reserved_Word = MS Jet 4.0
    -> Aggregator
TestFilter_6
    DEFAULT_VALUE = <UNFILTERED>
    TEST_LIST = "BOOL_OP,OR,COMPOSITE_TEST,""""""1"""""",TEST_CLAUSE,CASE_SENSITIVE_TEST @Value(_attr_name) CONTAINS_REGEX [^0-9a-zA-Z\-\s\_]",Field Name - Special Characters,"BOOL_OP,OR,COMPOSITE_TEST,""""""1"""""",TEST_CLAUSE,CASE_SENSITIVE_TEST @Value(_attr_name) CONTAINS_REGEX ^(\ )",Field Name - Leading space character,"BOOL_OP,OR,COMPOSITE_TEST,""""""1"""""",TEST_CLAUSE,CASE_SENSITIVE_TEST @Value(_attr_name) CONTAINS_REGEX (\ )",Field Name - Space character,"BOOL_OP,OR,COMPOSITE_TEST,""""""1"""""",TEST_CLAUSE,CASE_SENSITIVE_TEST @Value(_attr_name) CONTAINS_REGEX ^(\_)",Field Name - Leading Underscore,"BOOL_OP,OR,COMPOSITE_TEST,""""""1"""""",TEST_CLAUSE,CASE_SENSITIVE_TEST @Value(_attr_name) CONTAINS_REGEX ^[0-9]",Field Name - Leading Number/digit
    Field Name - Special Characters -> AttributeCreator_7
    Field Name - Leading space character -> AttributeCreator_4
    Field Name - Space character -> AttributeCreator_4
    Field Name - Leading Underscore -> AttributeCreator_5
    Field Name - Leading Number/digit -> AttributeCreator_8
    <UNFILTERED> -> Aggregator
AttributeCreator_7
    ATTR_TABLE = SET_TO _FieldName_Special Character = Special Character
    -> Aggregator
AttributeCreator_4
    ATTR_TABLE = SET_TO _FieldName_Special Character = Space character
    -> Aggregator
AttributeCreator_5
    ATTR_TABLE = SET_TO _FieldName_Special Character = Leading Underscore
    -> Aggregator
AttributeCreator_8
    ATTR_TABLE = SET_TO _FieldName_Special Character = Leading Numeral
    -> Aggregator
Note: ArcGIS field data types / https://desktop.arcgis.com/en/arcmap/latest/manage-data/geodatabases/arcgis-field-data-types.htm
Note: FAQ: What characters should not be used in ArcGIS for field names and table names? / https://support.esri.com/en/technical-article/000005588
Note: List of Microsoft Jet 4.0 reserved words / https://support.microsoft.com/en-us/help/321266/list-of-microsoft-jet-4-0-reserved-words
Note: List of reserved words in Access 2002 and in later versions of Access / https://support.microsoft.com/en-us/help/286335/list-of-reserved-words-in-access-2002-and-in-later-versions-of-access / Learn about Access reserved words and symbols / https://support.office.com/en-us/article/learn-about-access-reserved-words-and-symbols-ae9d9ada-3255-4b12-91a9-f855bdd9c5a2#__toc262648754
Aggregator
    ACCUM_ATTRS_NAME = Use Attributes From One Feature
    AGGREGATE_TYPE = Homogeneous Collection (If Possible)
    CONCAT_ATTRS = "_FieldName_Special Character" _FieldName_Reserved_Word
    GROUP_BY = _attr_name
    MODE = Geometry - Assemble One Level
    SEP = ,
    AGGREGATE -> FeatureMerger_8 [REQUESTOR]

Bookmark: Old Tests
Junction_8
    -> TestFilter_13 [off]
TestFilter_13 [off]
    DEFAULT_VALUE = <UNFILTERED>
    TEST_LIST = "BOOL_OP,OR,COMPOSITE_TEST,""""""1"""""",TEST_CLAUSE,TEST _attr_value ATTRIBUTE_VALUE_NULL """,Null Values,"BOOL_OP,OR,COMPOSITE_TEST,""""""1"""""",TEST_CLAUSE,TEST _attr_value ATTRIBUTE_IS_MISSING """,Missing Values,"BOOL_OP,OR,COMPOSITE_TEST,""""""1"""""",TEST_CLAUSE,TEST _attr_value ATTRIBUTE_IS_EMPTY """,Empty Values,"BOOL_OP,OR,COMPOSITE_TEST,""""""1"""""",TEST_CLAUSE,CASE_SENSITIVE_TEST @Value(_attr_value) CONTAINS_REGEX ^.*(?=.*\d)(?=.*[a-zA-Z]).*$",Regex Alpha & Numeric,"BOOL_OP,AND,COMPOSITE_TEST,""""""1"""""",TEST_CLAUSE,TEST @Value(_attr_value) TYPE NUM",Numeric Only - @Value(_attr_value) TYPE NUM,"BOOL_OP,AND,COMPOSITE_TEST,""""""1"""""",TEST_CLAUSE,TEST @Value(_attr_value) NOT_TYPE NUM",Alpha Only - @Value(_attr_value) NOT_TYPE NUM,"BOOL_OP,AND,COMPOSITE_TEST,""""""1"""""",TEST_CLAUSE,TEST @Value(_attr_value) TYPE ALPHANUM",Alphanumeric - @Value(_attr_value) NOT_TYPE NUM
    Null Values -> AttributeCreator_43 [off]
    Missing Values -> AttributeCreator_44 [off]
    Empty Values -> Junction_10 [off]
    Regex Alpha & Numeric -> AttributeCreator_36 [off]
    Numeric Only - @Value(_attr_value) TYPE NUM -> AttributeCreator_38 [off]
    Alpha Only - @Value(_attr_value) NOT_TYPE NUM -> AttributeCreator_37 [off]
AttributeCreator_43 [off]
    ATTR_TABLE = SET_TO _Contains NULL Values = TRUE - one or more attributes contain a NULL value
    -> Junction_10 [off]
AttributeCreator_44 [off]
    ATTR_TABLE = SET_TO _Contains Missing Values = TRUE - one or more attributes contain a Missing value
    -> Junction_10 [off]
AttributeCreator_36 [off]
    ATTR_TABLE = SET_TO FieldType_AlphaNumeric_Pass = TRUE - one or more attributes contain Alphanumeric Values
    -> Junction_10 [off]
Junction_10 [off]
    -> Junction_5 [off]
AttributeCreator_37 [off]
    ATTR_TABLE = SET_TO FieldType_Alpha_Pass = TRUE - one or more attributes contain Alpha Only Values
    -> Junction_5 [off]
AttributeCreator_38 [off]
    ATTR_TABLE = SET_TO FieldType_Numeric_Pass = TRUE - one or more attributes contain Numeric Only Values
    -> TestFilter_14 [off]
TestFilter_14 [off]
    DEFAULT_VALUE = Other Numeric
    TEST_LIST = "BOOL_OP,AND,COMPOSITE_TEST,""""""1"""""",TEST_CLAUSE,TEST @Value(_attr_value) TYPE INT",Integer @Value(_attr_value) TYPE INT,"BOOL_OP,AND,COMPOSITE_TEST,""""""1"""""",TEST_CLAUSE,TEST @Value(_attr_value) TYPE DOUBLE",Double @Value(_attr_value) TYPE DOUBLE
    Integer @Value(_attr_value) TYPE INT -> AttributeCreator_42 [off]
    Double @Value(_attr_value) TYPE DOUBLE -> AttributeCreator_40 [off]
    Other Numeric -> AttributeCreator_41 [off]
AttributeCreator_42 [off]
    ATTR_TABLE:
      SET_TO FieldType_Integer_Pass = TRUE - one or more attributes contain Integar values
      SET_TO FieldType_Double_Pass = TRUE - one or more attributes contain Non-Decimal Double values
    -> Junction_11 [off]
AttributeCreator_40 [off]
    ATTR_TABLE:
      SET_TO FieldType_Double_Pass = TRUE - one or more attributes contain Decimal Double values
      SET_TO FieldType_Boolean_Pass = FALSE
      SET_TO FieldType_Integer_Pass = FALSE
    -> Junction_11 [off]
AttributeCreator_41 [off]
    ATTR_TABLE:
      SET_TO FieldType_numeric_NOT_Double_or_Integer_Pass = TRUE - one or more attributes contain Numeric value that is not an Integar or Double
      SET_TO FieldType_Boolean_Pass = FALSE
    -> Junction_11 [off]
Junction_11 [off]
    -> Junction_5 [off]
Junction_5 [off]
    -> TestFilter_15 [off]
TestFilter_15 [off]
    DEFAULT_VALUE = <UNFILTERED>
    TEST_LIST = "BOOL_OP,OR,COMPOSITE_TEST,""""""1"""""",TEST_CLAUSE,TEST _attr_value ATTRIBUTE_IS_EMPTY """,Empty String
    Empty String -> AttributeCreator_46 [off]
    <UNFILTERED> -> AttributeRemover_3 [off]
AttributeCreator_46 [off]
    ATTR_TABLE = SET_TO _Contains Empty String Values = TRUE - one or more attributes contain an empty string value
    -> AttributeRemover_3 [off]
AttributeRemover_3 [off]
    REMOVE_ATTRS = Type_Pass_Boolean

Bookmark: Evaluate Field Types
TestFilter_17
    DEFAULT_VALUE = <UNFILTERED>
    TEST_LIST = "BOOL_OP,OR,COMPOSITE_TEST,""""""1"""""",TEST_CLAUSE,TEST _attr_value ATTRIBUTE_VALUE_NULL """,Null Values,"BOOL_OP,OR,COMPOSITE_TEST,""""""1"""""",TEST_CLAUSE,TEST _attr_value ATTRIBUTE_IS_MISSING """,Missing Values,"BOOL_OP,OR,COMPOSITE_TEST,""""""1"""""",TEST_CLAUSE,TEST _attr_value ATTRIBUTE_IS_EMPTY """,Empty Values
    Null Values -> AttributeCreator_49
    Empty Values -> AttributeCreator_50
    <UNFILTERED> -> TestFilter_12
AttributeCreator_49
    ATTR_TABLE = SET_TO _Contains NULL Values = TRUE - one or more attributes contain a NULL value
    -> Junction_14
AttributeCreator_50
    ATTR_TABLE = SET_TO _Contains Empty Values = TRUE - one or more attributes contain an Empty or Missing value
    -> Junction_14
Note: Checks for FME Standard Date/Time Format / Validate fields where dates are formatted to write to Esri file types
Junction_14
    -> DuplicateFilter_2
Note: FME Standard Date/Time Format: / https://docs.safe.com/fme/html/FME_Desktop_Documentation/FME_ReadersWriters/!Transformer_Parameters/standard_fme_date_time_format.htm
Note: Validate fields where dates are formatted to write to Esri file types
TestFilter_12
    DEFAULT_VALUE = Does not containa date that will be written to an Esri Date format
    TEST_LIST = "BOOL_OP,OR,COMPOSITE_TEST,""""""1"""""",TEST_CLAUSE,CASE_SENSITIVE_TEST @Value(_attr_value) CONTAINS_REGEX ^(1|2)[0-9]{3}(0[1-9]|1[0-2])(0[1-9]|[1-2][0-9]|3[0-1])$",four digit year: YYYYMMDD (eg 20170206),"BOOL_OP,OR,COMPOSITE_TEST,""""""1"""""",TEST_CLAUSE,CASE_SENSITIVE_TEST @Value(_attr_value) CONTAINS_REGEX ^(1[0-9]{3}|2[0-9]{3})(0[0-9]|1[0-2])([0-2][0-9]|3[0-1])(0[0-9]|1[0-2])(0[0-9]|[0-5][0-9])(0[0-9]|[0-5][0-9])$",Contains Text Matching an ISO8601 Date Time with no miliseconds/decimals and no formatting (eg 20190131094832),"BOOL_OP,OR,COMPOSITE_TEST,""""""1"""""",TEST_CLAUSE,CASE_SENSITIVE_TEST @Value(_attr_value) CONTAINS_REGEX ^(1[0-9]{3}|2[0-9]{3})(0[0-9]|1[0-2])([0-2][0-9]|3[0-1])(0[0-9]|1[0-2])(0[0-9]|[0-5][0-9])(0[0-9]|[0-5][0-9])(.(\d{7})|.(\d{6})|.(\d{5})|.(\d{4})|.(\d{3})|.(\d{2})|.(\d{1})|)?$",Contains Text Matching an ISO8601 Date Time with no formatting (eg 20170206111730.14323),"BOOL_OP,OR,COMPOSITE_TEST,""""""1"""""",TEST_CLAUSE,CASE_SENSITIVE_TEST @Value(_attr_value) CONTAINS_REGEX ^(1[0-9]{3}|2[0-9]{3})(0[0-9]|1[0-2])([0-2][0-9]|3[0-1])(0[0-9]|1[0-2])(0[0-9]|[0-5][0-9])(0[0-9]|[0-5][0-9])(.(\d{7})|.(\d{6})|.(\d{5})|.(\d{4})|.(\d{3})|.(\d{2})|.(\d{1})|)?(-|\+)([0-1][0-9]:\d\d)$",Contains Text Matching UTC offset Date Time eg 20170206111730.135-08:00,"BOOL_OP,OR,COMPOSITE_TEST,""""""1"""""",TEST_CLAUSE,CASE_SENSITIVE_TEST _attr_value ATTRIBUTE_VALUE_NULL """,Contains a Null Value,"BOOL_OP,OR,COMPOSITE_TEST,""""""1"""""",TEST_CLAUSE,CASE_SENSITIVE_TEST _attr_value ATTRIBUTE_IS_MISSING """,Contains a Missing Value
    four digit year: YYYYMMDD (eg 20170206) -> AttributeCreator_31
    Contains Text Matching an ISO8601 Date Time with no miliseconds/decimals and no formatting (eg 20190131094832) -> AttributeCreator_13
    Contains Text Matching an ISO8601 Date Time with no formatting (eg 20170206111730.14323) -> AttributeCreator_33
    Contains Text Matching UTC offset Date Time eg 20170206111730.135-08:00 -> AttributeCreator_14
    Contains a Null Value -> Junction_12
    Contains a Missing Value -> Junction_12
    Does not containa date that will be written to an Esri Date format -> AttributeCreator_35
AttributeCreator_31
    ATTR_TABLE:
      SET_TO _DateValue_WriteToShapeFile_YYYYMMDD = Pass: Simple date YYYYMMDD
      SET_TO _DateValue_WriteToFGDB_YYYYMMDD = Pass: Simple date YYYYMMDD
      SET_TO _DateValue_WriteToAGOL_YYYYMMDD = Pass: Simple date YYYYMMDD
    -> AttributeCreator_45
AttributeCreator_13
    ATTR_TABLE:
      SET_TO _DateValue_WriteToShapeFile_YYYYMMDDHHMMSS = Pass: Date & Time YYYYMMDDHHMMSS
      SET_TO _DateValue_WriteToFGDB_YYYYMMDDHHMMSS = Pass: Date & Time YYYYMMDDHHMMSS
      SET_TO _DateValue_WriteToAGOL_YYYYMMDDHHMMSS = Pass: Date & Time YYYYMMDDHHMMSS
    -> AttributeCreator_45
AttributeCreator_33
    ATTR_TABLE:
      SET_TO _DateValue_WriteToShapeFile = FAIL: Value contains Milliseconds
      SET_TO _DateValue_WriteToFGDB_YYYYMMDDHHMMSSs = Pass: Date & Time YYYYMMDDHHMMSS.mmm
      SET_TO _DateValue_WriteToAGOL_YYYYMMDDHHMMSSs = Pass: Date & Time YYYYMMDDHHMMSS.mmm
    -> AttributeCreator_45
AttributeCreator_14
    ATTR_TABLE:
      SET_TO _DateValue_WriteToShapeFile = FAIL: Value contains UTC offset
      SET_TO _DateValue_WriteToFGDB_[Datetime][UTC offset]_YYYYMMDDHHMMSSs(+/-)hh:mm = Pass: Date & Time YYYYMMDDHHMMSS.s(+/-)hh:mm
      SET_TO _DateValue_WriteToAGOL_[Datetime][UTC offset]_YYYYMMDDHHMMSSs(+/-)hh:mm = Pass: Date & Time YYYYMMDDHHMMSS.s(+/-)hh:mm
    -> AttributeCreator_45
AttributeCreator_45
    ATTR_TABLE = SET_TO FieldType_Date_Pass = TRUE - one or more attributes contain valid Date Values
    -> Junction_4
Junction_12 [off]
    -> Junction_4
AttributeCreator_35
    ATTR_TABLE = SET_TO _DateValue_Not a valid Date Field = One or more attribute values are not formated as a date that will be written to an FME Date field.
    -> Junction_4
Junction_4
    -> DuplicateFilter_2
